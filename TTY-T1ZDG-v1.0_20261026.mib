TTY-T4XDG-v1-4-MIB DEFINITIONS ::= BEGIN 
	IMPORTS
		enterprises, Integer32, OBJECT-TYPE 
            FROM SNMPv2-SMI
		DisplayString  
            FROM RFC1213-MIB 
    	IpAddress       
    		FROM RFC1155-SMI  
    	PhysAddress                        
    		FROM RFC1213-MIB; 
	
	ttyRoot 					OBJECT IDENTIFIER ::= {enterprises 52305}
	serverSysInfo				OBJECT IDENTIFIER ::= {ttyRoot 1}
	serverAssetInfo 			OBJECT IDENTIFIER ::= {ttyRoot 2}
	serverBmcInfo				OBJECT IDENTIFIER ::= {ttyRoot 3}  
	serverRemoteControl			OBJECT IDENTIFIER ::= {ttyRoot 4}
	serverSetUpOptionControl	OBJECT IDENTIFIER ::= {ttyRoot 5}
	serverTemperatureInfo		OBJECT IDENTIFIER ::= {ttyRoot 6}
	serverStatus				OBJECT IDENTIFIER ::= {ttyRoot 7}
	bmcNTPConf					OBJECT IDENTIFIER ::= {serverBmcInfo 4}
	bmcUserManagement			OBJECT IDENTIFIER ::= {serverBmcInfo 5}
	mediaRedirectionSettings	OBJECT IDENTIFIER ::= {serverBmcInfo 8}
	externalUserSettings		OBJECT IDENTIFIER ::= {serverBmcInfo 9}
	bmcDNSConf					OBJECT IDENTIFIER ::= {serverBmcInfo 10}
	--kvmMouseSetting				OBJECT IDENTIFIER ::= {serverBmcInfo 11}
	sslCertMessage				OBJECT IDENTIFIER ::= {serverBmcInfo 12}
	alarmSetting			OBJECT IDENTIFIER ::= {serverBmcInfo 13}
	--platformEventFilters		OBJECT IDENTIFIER ::= {serverBmcInfo 13}
	--firewallIPRulesConf		OBJECT IDENTIFIER ::= {serverBmcInfo 15}
	--firewallPortRulesConf		OBJECT IDENTIFIER ::= {serverBmcInfo 16}
	--firewallGeneralRulesConf	OBJECT IDENTIFIER ::= {serverBmcInfo 17}
	--videoSettings				OBJECT IDENTIFIER ::= {serverBmcInfo 18}
	logSettings					OBJECT IDENTIFIER ::= {serverBmcInfo 20}
	serviceSession				OBJECT IDENTIFIER ::= {serverBmcInfo 21}
	logPolicy					OBJECT IDENTIFIER ::= {logSettings 1}
	advancedLog					OBJECT IDENTIFIER ::= {logSettings 2}
	remoteSessionConf			OBJECT IDENTIFIER ::= {mediaRedirectionSettings 1}
	vmediaInstanceConf			OBJECT IDENTIFIER ::= {mediaRedirectionSettings 2}
	generalRADIUSConf			OBJECT IDENTIFIER ::= {externalUserSettings 1}
	sysFanConf					OBJECT IDENTIFIER ::= {serverAssetInfo 7}
	powerUnit					OBJECT IDENTIFIER ::= {serverAssetInfo 10}
	--powerConf					OBJECT IDENTIFIER ::= {powerUnit 2}
	--powerCommon					OBJECT IDENTIFIER ::= {powerUnit 3}
	serverPowerControl      	OBJECT IDENTIFIER ::= {serverRemoteControl 1}
	serverLocatedControl    	OBJECT IDENTIFIER ::= {serverRemoteControl 2}
	serverBootOptionControl    	OBJECT IDENTIFIER ::= {serverSetUpOptionControl 1}
	--eepromControl    			OBJECT IDENTIFIER ::= {serverSetUpOptionControl 2}
	healthStatus    			OBJECT IDENTIFIER ::= {serverStatus 1}
	hddStatus    				OBJECT IDENTIFIER ::= {serverStatus 2}
	
--serverSysInfo start
	hostname OBJECT-TYPE
		SYNTAX OCTET STRING
		MAX-ACCESS read-only
		STATUS current
		DESCRIPTION
			""
		::= { serverSysInfo 1 }
--	platformInfo OBJECT-TYPE
--		SYNTAX OCTET STRING
--		MAX-ACCESS read-only
--		STATUS current
--		DESCRIPTION
--			""
--		::= { serverSysInfo 2 }
	biosVersion OBJECT-TYPE
		SYNTAX OCTET STRING
		MAX-ACCESS read-only
		STATUS current
		DESCRIPTION
			""
		::= { serverSysInfo 3 }
	mainBoardCpldVersion OBJECT-TYPE
		SYNTAX OCTET STRING
		MAX-ACCESS read-only
		STATUS current
		DESCRIPTION
			""
		::= { serverSysInfo 4 }
	backPlaneCpldVersion OBJECT-TYPE
		SYNTAX OCTET STRING
		MAX-ACCESS read-only
		STATUS current
		DESCRIPTION
			""
		::= { serverSysInfo 5 }
	bmcFwVersion OBJECT-TYPE
		SYNTAX OCTET STRING
		MAX-ACCESS read-only
		STATUS current
		DESCRIPTION
			""
		::= { serverSysInfo 6 }
	bmcFwBuildTime OBJECT-TYPE
		SYNTAX OCTET STRING
		MAX-ACCESS read-only
		STATUS current
		DESCRIPTION
			""
		::= { serverSysInfo 7 }
	rcVersion OBJECT-TYPE
		SYNTAX OCTET STRING
		MAX-ACCESS read-only
		STATUS current
		DESCRIPTION
			""
		::= { serverSysInfo 8 }
	microCodeVersion OBJECT-TYPE
		SYNTAX OCTET STRING
		MAX-ACCESS read-only
		STATUS current
		DESCRIPTION
			""
		::= { serverSysInfo 9 }
--	meVersion OBJECT-TYPE
--		SYNTAX OCTET STRING
--		MAX-ACCESS read-only
--		STATUS current
--		DESCRIPTION
--			""
--		::= { serverSysInfo 10 }
	productName OBJECT-TYPE
		SYNTAX OCTET STRING
		MAX-ACCESS read-only
		STATUS current
		DESCRIPTION
			""
		::= { serverSysInfo 11 }  
	productSN OBJECT-TYPE
		SYNTAX OCTET STRING
		MAX-ACCESS read-only
		STATUS current
		DESCRIPTION
			""
		::= { serverSysInfo 12 }
	totalpower OBJECT-TYPE
		SYNTAX OCTET STRING
		MAX-ACCESS read-only
		STATUS current
		DESCRIPTION
			""
		::= { serverSysInfo 13 }  
--serverSysInfo end
--discreteSensorTable start
	discreteSensorTable OBJECT-TYPE
		SYNTAX SEQUENCE OF DiscreteSensorEntry
		MAX-ACCESS not-accessible
		STATUS current
		DESCRIPTION
			""
		::= { serverAssetInfo 1 }
	discreteSensorEntry OBJECT-TYPE
		SYNTAX DiscreteSensorEntry
		MAX-ACCESS not-accessible
		STATUS current
		DESCRIPTION
			""
		INDEX { discreteSensorIndex }
		::= { discreteSensorTable 1 }
	DiscreteSensorEntry ::=
		SEQUENCE {
			discreteSensorIndex		Integer32,
			discreteSensorName		DisplayString,
			discreteSensorStatus	DisplayString,
			discreteSensorValue		DisplayString,
			discreteSensorLowNRT	DisplayString,
			discreteSensorLowCT		DisplayString,
			discreteSensorLowNCT	DisplayString,
			discreteSensorUpNCT		DisplayString,
			discreteSensorUpCT		DisplayString,
			discreteSensorUpNRT		DisplayString
		}
	discreteSensorIndex OBJECT-TYPE
		SYNTAX Integer32
		MAX-ACCESS read-only
		STATUS current
		DESCRIPTION
			""
		::= { discreteSensorEntry 1 }
	discreteSensorName OBJECT-TYPE
		SYNTAX DisplayString
		MAX-ACCESS read-only
		STATUS current
		DESCRIPTION
			""
		::= { discreteSensorEntry 2 }
	discreteSensorStatus OBJECT-TYPE
		SYNTAX 			DisplayString
		MAX-ACCESS		read-only
		STATUS			current
		DESCRIPTION 
		"
			The sensor status associated with the temperature sensor of this entry.
		"
		::= {discreteSensorEntry 3} 
	discreteSensorValue OBJECT-TYPE
		SYNTAX DisplayString
		MAX-ACCESS read-only
		STATUS current
		DESCRIPTION
			""
		::= { discreteSensorEntry 4 }		
	discreteSensorLowNRT OBJECT-TYPE
		SYNTAX 			DisplayString 
		MAX-ACCESS		read-only
		STATUS			current
		DESCRIPTION 
		"
			The lower non-recoverable threshold associated with the temperature sensor of this entry.
		"
		::= {discreteSensorEntry 5}   
				  
	discreteSensorLowCT OBJECT-TYPE
		SYNTAX 			DisplayString
		MAX-ACCESS		read-only
		STATUS			current
		DESCRIPTION 
		"
			The lower critical threshold associated with the temperature sensor of this entry.
		"
		::= {discreteSensorEntry 6}
	      		  
	discreteSensorLowNCT OBJECT-TYPE
		SYNTAX 			DisplayString 
		MAX-ACCESS		read-only
		STATUS			current
		DESCRIPTION 
		"
			The lower non-critical threshold associated with the temperature sensor of this entry.
		"
		::= {discreteSensorEntry 7}
			  
	discreteSensorUpNCT OBJECT-TYPE
		SYNTAX 			DisplayString 
		MAX-ACCESS		read-only
		STATUS			current
		DESCRIPTION 
		"
			The upper non-critical threshold associated with the temperature sensor of this entry.
		"
		::= {discreteSensorEntry 8}
	      		  
	discreteSensorUpCT OBJECT-TYPE
		SYNTAX 			DisplayString 
		MAX-ACCESS		read-only
		STATUS			current
		DESCRIPTION 
		"
			The upper critical threshold associated with the temperature sensor of this entry.
		"
		::= {discreteSensorEntry 9}
		  
	discreteSensorUpNRT OBJECT-TYPE
		SYNTAX 			DisplayString 
		MAX-ACCESS		read-only
		STATUS			current
		DESCRIPTION 
		"
			The upper non-recoverable threshold associated with the temperature sensor of this entry.
		"
		::= {discreteSensorEntry 10}		
--discreteSensorTable end
--fruTable start
	fruTable OBJECT-TYPE
		SYNTAX SEQUENCE OF FruEntry
		MAX-ACCESS not-accessible
		STATUS current
		DESCRIPTION
			""
		::= { serverAssetInfo 2 }
	fruEntry OBJECT-TYPE
		SYNTAX FruEntry
		MAX-ACCESS not-accessible
		STATUS current
		DESCRIPTION
			""
		INDEX { fruIndex }
		::= { fruTable 1 }
	FruEntry ::=
		SEQUENCE {
			fruIndex				Integer32,
			fruDeviceID				Integer32,
			fruDeviceName			OCTET STRING,
			fruBoardProductName		OCTET STRING,
			fruBoardSerialNum		OCTET STRING,
			fruBoardPartNum			OCTET STRING,
			fruBoardMfrName			OCTET STRING,
			fruBoardExtra			OCTET STRING,
			fruProductMfrName		OCTET STRING,
			fruProductName			OCTET STRING,
			fruProductPartNum		OCTET STRING,
			fruProductVersion		OCTET STRING,
			fruProductSerialNum		OCTET STRING,
			fruProductAssetTag		OCTET STRING,
			fruProductExtra 		OCTET STRING,
			fruChassisType			OCTET STRING,
			fruChassisPartNum		OCTET STRING,
			fruChassisSerialNum		OCTET STRING,
			fruChassisExtra			OCTET STRING
		}
	fruIndex OBJECT-TYPE
		SYNTAX Integer32
		MAX-ACCESS read-only
		STATUS current
		DESCRIPTION
			""
		::= { fruEntry 1 }
	fruDeviceID OBJECT-TYPE
		SYNTAX Integer32
		MAX-ACCESS read-only
		STATUS current
		DESCRIPTION
			""
		::= { fruEntry 2 }
	fruDeviceName OBJECT-TYPE
		SYNTAX OCTET STRING
		MAX-ACCESS read-only
		STATUS current
		DESCRIPTION
			""
		::= { fruEntry 3 }
	fruBoardProductName OBJECT-TYPE
		SYNTAX OCTET STRING
		MAX-ACCESS read-only
		STATUS current
		DESCRIPTION
			""
		::= { fruEntry 4 }
	fruBoardSerialNum OBJECT-TYPE
		SYNTAX OCTET STRING
		MAX-ACCESS read-only
		STATUS current
		DESCRIPTION
			""
		::= { fruEntry 5 }
	fruBoardPartNum OBJECT-TYPE
		SYNTAX OCTET STRING
		MAX-ACCESS read-only
		STATUS current
		DESCRIPTION
			""
		::= { fruEntry 6 }
	fruBoardMfrName OBJECT-TYPE
		SYNTAX OCTET STRING
		MAX-ACCESS read-only
		STATUS current
		DESCRIPTION
			""
		::= { fruEntry 7 }
	fruBoardExtra OBJECT-TYPE
		SYNTAX OCTET STRING
		MAX-ACCESS read-only
		STATUS current
		DESCRIPTION
			""
		::= { fruEntry 8 }
	fruProductMfrName OBJECT-TYPE
		SYNTAX OCTET STRING
		MAX-ACCESS read-only
		STATUS current
		DESCRIPTION
			""
		::= { fruEntry 9 }
	fruProductName OBJECT-TYPE
		SYNTAX OCTET STRING
		MAX-ACCESS read-only
		STATUS current
		DESCRIPTION
			""
		::= { fruEntry 10 }
	fruProductPartNum OBJECT-TYPE
		SYNTAX OCTET STRING
		MAX-ACCESS read-only
		STATUS current
		DESCRIPTION
			""
		::= { fruEntry 11 }
	fruProductVersion OBJECT-TYPE
		SYNTAX OCTET STRING
		MAX-ACCESS read-only
		STATUS current
		DESCRIPTION
			""
		::= { fruEntry 12 }
	fruProductSerialNum OBJECT-TYPE
		SYNTAX OCTET STRING
		MAX-ACCESS read-only
		STATUS current
		DESCRIPTION
			""
		::= { fruEntry 13 }
	fruProductAssetTag OBJECT-TYPE
		SYNTAX OCTET STRING
		MAX-ACCESS read-write
		STATUS current
		DESCRIPTION
			"only the id==0 can write asset tag"
		::= { fruEntry 14 }
	fruProductExtra OBJECT-TYPE
		SYNTAX OCTET STRING
		MAX-ACCESS read-only
		STATUS current
		DESCRIPTION
			""
		::= { fruEntry 15 }
	fruChassisType OBJECT-TYPE
		SYNTAX OCTET STRING
		MAX-ACCESS read-only
		STATUS current
		DESCRIPTION
			""
		::= { fruEntry 16 }
	fruChassisPartNum OBJECT-TYPE
		SYNTAX OCTET STRING
		MAX-ACCESS read-only
		STATUS current
		DESCRIPTION
			""
		::= { fruEntry 17 }
	fruChassisSerialNum OBJECT-TYPE
		SYNTAX OCTET STRING
		MAX-ACCESS read-only
		STATUS current
		DESCRIPTION
			""
		::= { fruEntry 18 }
	fruChassisExtra OBJECT-TYPE
		SYNTAX OCTET STRING
		MAX-ACCESS read-only
		STATUS current
		DESCRIPTION
			""
		::= { fruEntry 19 }
--fruTable end
--cpuInfoTable start
	cpuInfoTable OBJECT-TYPE
		SYNTAX SEQUENCE OF CpuInfoEntry
		MAX-ACCESS not-accessible
		STATUS current
		DESCRIPTION
			""
		::= { serverAssetInfo 3 }
	cpuInfoEntry OBJECT-TYPE
		SYNTAX CpuInfoEntry
		MAX-ACCESS not-accessible
		STATUS current
		DESCRIPTION
			""
		INDEX { cpuIndex }
		::= { cpuInfoTable 1 }
	CpuInfoEntry ::=
		SEQUENCE {
			cpuIndex		Integer32,
			cpuType			OCTET STRING,
			cpuName			OCTET STRING,
			cpuCurrentSpeed		OCTET STRING,
			cpuCoreCount		Integer32,
			cpuL1Cache		OCTET STRING,
			cpuL2Cache		OCTET STRING,
			cpuL3Cache		OCTET STRING,
			cpuThreadNum		Integer32,
			cpuMaxSpeed		OCTET STRING,
			cpuInstruction		OCTET STRING,
			cpuManufacturer		OCTET STRING,
			cpuProcessorId		OCTET STRING,
			cpuSerialnum		OCTET STRING,
			cpuTemprature		OCTET STRING,
			cpuPresence			OCTET STRING,
			cpuHealth			Integer32
		}
	cpuIndex OBJECT-TYPE
		SYNTAX Integer32
		MAX-ACCESS read-only
		STATUS current
		DESCRIPTION
			""
		::= { cpuInfoEntry 1 }
	cpuType OBJECT-TYPE
		SYNTAX OCTET STRING
		MAX-ACCESS read-only
		STATUS current
		DESCRIPTION
			""
		::= { cpuInfoEntry 2 }
	cpuName OBJECT-TYPE
		SYNTAX OCTET STRING
		MAX-ACCESS read-only
		STATUS current
		DESCRIPTION
			""
		::= { cpuInfoEntry 3 }
	cpuCurrentSpeed OBJECT-TYPE
		SYNTAX OCTET STRING
		MAX-ACCESS read-only
		STATUS current
		DESCRIPTION
			""
		::= { cpuInfoEntry 4 }
	cpuCoreCount OBJECT-TYPE
		SYNTAX Integer32{ NA(-1)}
		MAX-ACCESS read-only
		STATUS current
		DESCRIPTION
			""
		::= { cpuInfoEntry 5 }
	cpuL1Cache OBJECT-TYPE
		SYNTAX OCTET STRING
		MAX-ACCESS read-only
		STATUS current
		DESCRIPTION
			""
		::= { cpuInfoEntry 6 }
	cpuL2Cache OBJECT-TYPE
		SYNTAX OCTET STRING
		MAX-ACCESS read-only
		STATUS current
		DESCRIPTION
			""
		::= { cpuInfoEntry 7 }
	cpuL3Cache OBJECT-TYPE
		SYNTAX OCTET STRING
		MAX-ACCESS read-only
		STATUS current
		DESCRIPTION
			""
		::= { cpuInfoEntry 8 }
	cpuThreadNum OBJECT-TYPE
		SYNTAX Integer32{ NA(-1)}
		MAX-ACCESS read-only
		STATUS current
		DESCRIPTION
			""
		::= { cpuInfoEntry 9 }
	cpuMaxSpeed OBJECT-TYPE
		SYNTAX OCTET STRING
		MAX-ACCESS read-only
		STATUS current
		DESCRIPTION
			""
		::= { cpuInfoEntry 10 }
	cpuInstruction OBJECT-TYPE
		SYNTAX OCTET STRING
		MAX-ACCESS read-only
		STATUS current
		DESCRIPTION
			""
		::= { cpuInfoEntry 11 }
	cpuManufacturer OBJECT-TYPE
		SYNTAX OCTET STRING
		MAX-ACCESS read-only
		STATUS current
		DESCRIPTION
			""
		::= { cpuInfoEntry 12 }
	cpuProcessorId OBJECT-TYPE
		SYNTAX OCTET STRING
		MAX-ACCESS read-only
		STATUS current
		DESCRIPTION
			""
		::= { cpuInfoEntry 13 }
	cpuSerialnum OBJECT-TYPE
		SYNTAX OCTET STRING
		MAX-ACCESS read-only
		STATUS current
		DESCRIPTION
			""
		::= { cpuInfoEntry 14 }
	cpuTemprature OBJECT-TYPE
		SYNTAX OCTET STRING
		MAX-ACCESS read-only
		STATUS current
		DESCRIPTION
			""
		::= { cpuInfoEntry 15 }
	cpuPresence OBJECT-TYPE
		SYNTAX OCTET STRING
		MAX-ACCESS read-only
		STATUS current
		DESCRIPTION
			""
		::= { cpuInfoEntry 16 }
	cpuHealth OBJECT-TYPE
		SYNTAX Integer32{ normal(0), abnormal(1), absent(2) }
		MAX-ACCESS read-only
		STATUS current
		DESCRIPTION
			""
		::= { cpuInfoEntry 17 }
--cpuInfoTable end
--memoryInfoTable start
	memoryInfoTable OBJECT-TYPE
		SYNTAX SEQUENCE OF MemoryInfoEntry
		MAX-ACCESS not-accessible
		STATUS current
		DESCRIPTION
			""
		::= { serverAssetInfo 4 }
	memoryInfoEntry OBJECT-TYPE
		SYNTAX MemoryInfoEntry
		MAX-ACCESS not-accessible
		STATUS current
		DESCRIPTION
			""
		INDEX { memoryInfoIndex }
		::= { memoryInfoTable 1 }
	MemoryInfoEntry ::=
		SEQUENCE {
			memoryInfoIndex			Integer32,
			memoryInfoSlot			OCTET STRING,
			memoryInfoType			OCTET STRING,
			memoryInfoSize			OCTET STRING,
			memoryInfoSpeed			OCTET STRING,
			memoryInfoRateSpeed  	OCTET STRING,
			memoryInfoMfr			OCTET STRING,
			memoryInfoPartNum		OCTET STRING,
			memoryInfoSerialNum		OCTET STRING,
			memoryInfoTemperature 	OCTET STRING,
			memoryPresence			OCTET STRING,
			memoryHealth			Integer32
--			memoryInfoVoltage 		OCTET STRING
		}
	memoryInfoIndex OBJECT-TYPE
		SYNTAX Integer32
		MAX-ACCESS read-only
		STATUS current
		DESCRIPTION
			""
		::= { memoryInfoEntry 1 }
	memoryInfoSlot OBJECT-TYPE
		SYNTAX OCTET STRING
		MAX-ACCESS read-only
		STATUS current
		DESCRIPTION
			""
		::= { memoryInfoEntry 2 }
	memoryInfoType OBJECT-TYPE
		SYNTAX OCTET STRING
		MAX-ACCESS read-only
		STATUS current
		DESCRIPTION
			""
		::= { memoryInfoEntry 3 }
	memoryInfoSize OBJECT-TYPE
		SYNTAX OCTET STRING
		MAX-ACCESS read-only
		STATUS current
		DESCRIPTION
			""
		::= { memoryInfoEntry 4 }
	memoryInfoSpeed OBJECT-TYPE
		SYNTAX OCTET STRING
		MAX-ACCESS read-only
		STATUS current
		DESCRIPTION
			""
		::= { memoryInfoEntry 5 }
	memoryInfoRateSpeed OBJECT-TYPE
		SYNTAX OCTET STRING
		MAX-ACCESS read-only
		STATUS current
		DESCRIPTION
			""
		::= { memoryInfoEntry 6 }
	memoryInfoMfr OBJECT-TYPE
		SYNTAX OCTET STRING
		MAX-ACCESS read-only
		STATUS current
		DESCRIPTION
			""
		::= { memoryInfoEntry 7 }
	memoryInfoSerialNum OBJECT-TYPE
		SYNTAX OCTET STRING
		MAX-ACCESS read-only
		STATUS current
		DESCRIPTION
			""
		::= { memoryInfoEntry 8 }
	memoryInfoTemperature OBJECT-TYPE
		SYNTAX OCTET STRING
		MAX-ACCESS read-only
		STATUS current
		DESCRIPTION
			""
		::= { memoryInfoEntry 9 }
	memoryInfoPartNum OBJECT-TYPE
		SYNTAX OCTET STRING
		MAX-ACCESS read-only
		STATUS current
		DESCRIPTION
			""
		::= { memoryInfoEntry 10 }
	memoryPresence OBJECT-TYPE
		SYNTAX OCTET STRING
		MAX-ACCESS read-only
		STATUS current
		DESCRIPTION
			""
		::= { memoryInfoEntry 11 }
	memoryHealth OBJECT-TYPE
		SYNTAX Integer32{ normal(0), abnormal(1), absent(2) }
		MAX-ACCESS read-only
		STATUS current
		DESCRIPTION
			""
		::= { memoryInfoEntry 12 }
--	memoryInfoVoltage OBJECT-TYPE
--		SYNTAX OCTET STRING
--		MAX-ACCESS read-only
--		STATUS current
--		DESCRIPTION
--			""
--		::= { memoryInfoEntry 13 }
--memoryInfoTable end
--pcieInfoTable start
	pcieInfoTable	OBJECT-TYPE
	    SYNTAX     SEQUENCE OF PcieInfoEntry
	    MAX-ACCESS read-only
	    STATUS     current
	    DESCRIPTION
	           "The table of PCIE information relevant to this entity's PCIE"
			::= {serverAssetInfo 5}
			
	pcieInfoEntry OBJECT-TYPE
	    SYNTAX     PcieInfoEntry
	    MAX-ACCESS read-only
	    STATUS     current
	    DESCRIPTION
	           "The PCIE information associated with the PCIE of this entry."
	    INDEX   { 
	    		  pcieInfoIndex
	            }
	    ::= { pcieInfoTable 1 }   
	
	PcieInfoEntry ::= SEQUENCE {
	    pcieInfoIndex					Integer32,
		pcieInfoNo						DisplayString,
		pcieInfoSlot		    		DisplayString,
		pcieInfoBusNo					DisplayString,
		pcieInfoDevNo					DisplayString,
		pcieInfoFuncNo					DisplayString,
--	    pcieInfoMac						DisplayString,
	    pcieInfoVendor					DisplayString,
	    pcieInfoDeviceType				DisplayString,
		pcieInfoDeviceDescription		DisplayString,
--		pcieInfoNetworkPortType			DisplayString,
--		pcieInfoNetworkPortSpeed		DisplayString,
	    pcieInfoRootBDF					DisplayString,
		pcieInfoRatedWidth				DisplayString,
		pcieInfoRatedSpeed				DisplayString,
		pcieInfoCurWidth				DisplayString,
		pcieInfoCurSpeed				DisplayString,
		pcieInfoCPUResource				DisplayString,
		pcieInfoHealth					Integer32,
		pcieInfoStatusDescription		DisplayString
	}  
	pcieInfoIndex  OBJECT-TYPE
		SYNTAX 			Integer32 
		MAX-ACCESS		read-only
		STATUS			current
		DESCRIPTION 
		"
			The index value which uniquely identifies 
			the interface to which this entry is applicable.
		"
		::= {pcieInfoEntry 1}    
	pcieInfoNo  OBJECT-TYPE
		SYNTAX 			DisplayString 
		MAX-ACCESS		read-only
		STATUS			current
		DESCRIPTION 
		"
			The device index associated with the PCIE of this entry
		"
		::= {pcieInfoEntry 2}
	pcieInfoSlot  OBJECT-TYPE
		SYNTAX 			DisplayString 
		MAX-ACCESS		read-only
		STATUS			current
		DESCRIPTION 
		"
			The Slot associated with the PCIE of this entry 
		"
		::= {pcieInfoEntry 3}
	pcieInfoBusNo  OBJECT-TYPE
		SYNTAX 			DisplayString 
		MAX-ACCESS		read-only
		STATUS			current
		DESCRIPTION 
		"
			The bus number associated with the PCIE of this entry
		"
		::= {pcieInfoEntry 4}
	pcieInfoDevNo  OBJECT-TYPE
		SYNTAX 			DisplayString 
		MAX-ACCESS		read-only
		STATUS			current
		DESCRIPTION 
		"
			The device number associated with the PCIE of this entry
		"
		::= {pcieInfoEntry 5}
	pcieInfoFuncNo  OBJECT-TYPE
		SYNTAX 			DisplayString 
		MAX-ACCESS		read-only
		STATUS			current
		DESCRIPTION 
		"
			The function number associated with the PCIE of this entry
		"
		::= {pcieInfoEntry 6}
--    pcieInfoMac  OBJECT-TYPE
--		SYNTAX 			DisplayString 
--		MAX-ACCESS		read-only
--		STATUS			current
--		DESCRIPTION 
--		"
--			The mac address associated with the PCIE of this entry 
--		"
--		::= {pcieInfoEntry 7}
    pcieInfoVendor  OBJECT-TYPE
		SYNTAX 			DisplayString 
		MAX-ACCESS		read-only
		STATUS			current
		DESCRIPTION 
		"
			The vendor associated with the PCIE of this entry 
		"
		::= {pcieInfoEntry 7}
	pcieInfoDeviceType  OBJECT-TYPE
		SYNTAX 			DisplayString 
		MAX-ACCESS		read-only
		STATUS			current
		DESCRIPTION 
		"
			The device type associated with the PCIE of this entry 
		"
		::= {pcieInfoEntry 8}
	pcieInfoDeviceDescription  OBJECT-TYPE
		SYNTAX 			DisplayString 
		MAX-ACCESS		read-only
		STATUS			current
		DESCRIPTION 
		"
			The deviceDescription associated with the PCIE of this entry 
		"
		::= {pcieInfoEntry 9}  

--	pcieInfoNetworkPortType  OBJECT-TYPE
--		SYNTAX 			DisplayString 
--		MAX-ACCESS		read-only
--		STATUS			current
--		DESCRIPTION 
--		"
--			The Network Port Type associated with the PCIE of this entry 
--		"
--		::= {pcieInfoEntry 11}
--	pcieInfoNetworkPortSpeed  OBJECT-TYPE
--		SYNTAX 			DisplayString 
--		MAX-ACCESS		read-only
--		STATUS			current
--		DESCRIPTION 
--		"
--			The Network Port Speed associated with the PCIE of this entry 
--		"
--		::= {pcieInfoEntry 12}
	pcieInfoRootBDF  OBJECT-TYPE
		SYNTAX 			DisplayString 
		MAX-ACCESS		read-only
		STATUS			current
		DESCRIPTION 
		"
			The RootBDF associated with the PCIE of this entry
		"
		::= {pcieInfoEntry 10} 		
	pcieInfoRatedWidth  OBJECT-TYPE
		SYNTAX 			DisplayString 
		MAX-ACCESS		read-only
		STATUS			current
		DESCRIPTION 
		"
			The rated width associated with the PCIE of this entry 
		"
		::= {pcieInfoEntry 11}
	pcieInfoRatedSpeed  OBJECT-TYPE
		SYNTAX 			DisplayString 
		MAX-ACCESS		read-only
		STATUS			current
		DESCRIPTION 
		"
			The rated speed associated with the PCIE of this entry 
		"
		::= {pcieInfoEntry 12}
	pcieInfoCurWidth  OBJECT-TYPE
		SYNTAX 			DisplayString 
		MAX-ACCESS		read-only
		STATUS			current
		DESCRIPTION 
		"
			The current width associated with the PCIE of this entry 
		"
		::= {pcieInfoEntry 13} 
	pcieInfoCurSpeed  OBJECT-TYPE
		SYNTAX 			DisplayString 
		MAX-ACCESS		read-only
		STATUS			current
		DESCRIPTION 
		"
			The current speed associated with the PCIE of this entry 
		"
		::= {pcieInfoEntry 14}	
	pcieInfoCPUResource  OBJECT-TYPE
		SYNTAX 			DisplayString 
		MAX-ACCESS		read-only
		STATUS			current
		DESCRIPTION 
		"
			The device CPU resource associated with the PCIE of this entry 
		"
		::= {pcieInfoEntry 15}
	pcieInfoHealth  OBJECT-TYPE
		SYNTAX 			Integer32 { normal(0), abnormal(1)}
		MAX-ACCESS		read-only
		STATUS			current
		DESCRIPTION 
		"
			The health associated with the PCIE of this entry 
		"
		::= {pcieInfoEntry 16}
	pcieInfoStatusDescription  OBJECT-TYPE
		SYNTAX 			DisplayString 
		MAX-ACCESS		read-only
		STATUS			current
		DESCRIPTION 
		"
			The network status associated with the PCIE of this entry 
		"
		::= {pcieInfoEntry 17}
--pcieInfoTable end
--fanInfoTable start
	fanInfoTable	OBJECT-TYPE
	    SYNTAX     SEQUENCE OF FanInfoEntry
	    MAX-ACCESS read-only
	    STATUS     current
	    DESCRIPTION
	           "The table of FAN information relevant to this entity's FAN"
			::= {serverAssetInfo 6}
			
	fanInfoEntry OBJECT-TYPE
	    SYNTAX     FanInfoEntry
	    MAX-ACCESS read-only
	    STATUS     current
	    DESCRIPTION
	           "The FAN information associated with the FAN of this entry."
	    INDEX   { 
	    		  fanInfoIndex
	            }
	    ::= { fanInfoTable 1 }   
	
	FanInfoEntry ::= SEQUENCE {
	    fanInfoIndex		Integer32,
	    fanInfoFanName		DisplayString,
		fanInfoSpeedIn		DisplayString,
		fanInfoSpeedOut		DisplayString,
		fanInfoDutyRatio	DisplayString,
		fanInfoHealth	Integer32
	}  
	fanInfoIndex  OBJECT-TYPE
		SYNTAX 			Integer32 
		MAX-ACCESS		read-only
		STATUS			current
		DESCRIPTION 
		"
			The index value which uniquely identifies 
			the interface to which this entry is applicable.
		"
		::= {fanInfoEntry 1}    
	fanInfoFanName  OBJECT-TYPE
		SYNTAX 			DisplayString 
		MAX-ACCESS		read-only
		STATUS			current
		DESCRIPTION 
		"
			The fan's name associated with the FAN of this entry
		"
		::= {fanInfoEntry 2}
	fanInfoSpeedIn  OBJECT-TYPE
		SYNTAX 			DisplayString 
		MAX-ACCESS		read-only
		STATUS			current
		DESCRIPTION 
		"
			The fan's inlet speed associated with the FAN of this entry
		"
		::= {fanInfoEntry 3}
	fanInfoSpeedOut  OBJECT-TYPE
		SYNTAX 			DisplayString 
		MAX-ACCESS		read-only
		STATUS			current
		DESCRIPTION 
		"
			The fan's outlet speed associated with the FAN of this entry
		"
		::= {fanInfoEntry 4}
	fanInfoDutyRatio  OBJECT-TYPE
		SYNTAX 			DisplayString 
		MAX-ACCESS		read-write
		STATUS			current
		DESCRIPTION 
		"
			The fan's duty ratio associated with the FAN of this entry, must >= 25%
		"
		::= {fanInfoEntry 5}
	fanInfoHealth  OBJECT-TYPE
		SYNTAX 			Integer32 { normal(0), abnormal(1), absent(2) }
		MAX-ACCESS		read-only
		STATUS			current
		DESCRIPTION 
		"
			The fan's health status associated with the FAN of this entry
		"
		::= {fanInfoEntry 6}
--fanInfoTable end
--sysFanConf start
	fanControlMode  OBJECT-TYPE
		SYNTAX 			Integer32{
						balance(0),
						manual(1),
						performance(2)
			}
		MAX-ACCESS		read-write
		STATUS			current
		DESCRIPTION 
		"
			The fan's mode speed associated with the FAN
		"
		::= {sysFanConf 1}
--sysFanConf end
--nvmeDiskInfoTable start
	nvmeDiskInfoTable	OBJECT-TYPE
	    SYNTAX     SEQUENCE OF NvmeDiskInfoEntry
	    MAX-ACCESS read-only
	    STATUS     current
	    DESCRIPTION
	           "The table of NvmeDisk information relevant to this entity's Nvme"
			::= {serverAssetInfo 8}
			
	nvmeDiskInfoEntry OBJECT-TYPE
	    SYNTAX     NvmeDiskInfoEntry
	    MAX-ACCESS read-only
	    STATUS     current
	    DESCRIPTION
	           "The NvmeDisk information associated with the disk of this entry."
	    INDEX   { 
				  nvmeDiskInfoIndex
	            }
	    ::= { nvmeDiskInfoTable 1 }   
	
	NvmeDiskInfoEntry ::= SEQUENCE {
	  	nvmeDiskInfoIndex  			Integer32,
	    nvmeDiskInfoLocation		DisplayString,
		nvmeDiskInfoProtocol		DisplayString, 
		nvmeDiskInfoFWVersion		DisplayString,
	    nvmeDiskInfoModel			DisplayString,
		nvmeDiskInfoMfr				DisplayString,
	    nvmeDiskInfoSerialNo		DisplayString,
		nvmeDiskInfoLinkSpeed		DisplayString,
		nvmeDiskInfoCapacity		DisplayString,
		nvmeDiskInfoTemp			DisplayString,
		nvmeDiskInfoPdlu  			Integer32,
		nvmeDiskInfoStatus			Integer32
	   }
	
	nvmeDiskInfoIndex  OBJECT-TYPE
		SYNTAX 			Integer32 
		MAX-ACCESS		read-only
		STATUS			current
		DESCRIPTION 
		"
			The index value which uniquely identifies the interface to which this entry is applicable.
		"
		::= {nvmeDiskInfoEntry 1}
	     		  
	nvmeDiskInfoLocation  OBJECT-TYPE
		SYNTAX 			DisplayString 
		MAX-ACCESS		read-only
		STATUS			current
		DESCRIPTION 
		"
			The location associated with the NvmeDisk of this entry.
		"
		::= {nvmeDiskInfoEntry 2}
		
	nvmeDiskInfoProtocol  OBJECT-TYPE
		SYNTAX 			DisplayString
		MAX-ACCESS		read-only
		STATUS			current
		DESCRIPTION 
		"
			The protocol associated with the NvmeDisk of this entry .
		"
		::= {nvmeDiskInfoEntry 3}
	nvmeDiskInfoFWVersion  OBJECT-TYPE
		SYNTAX 			DisplayString
		MAX-ACCESS		read-only
		STATUS			current
		DESCRIPTION 
		"
			The FWVersion associated with the NvmeDisk of this entry .
		"
		::= {nvmeDiskInfoEntry 4}
	nvmeDiskInfoModel  OBJECT-TYPE
		SYNTAX 			DisplayString
		MAX-ACCESS		read-only
		STATUS			current
		DESCRIPTION 
		"
			The Model associated with the NvmeDisk of this entry .
		"
		::= {nvmeDiskInfoEntry 5}
		  
	nvmeDiskInfoMfr  OBJECT-TYPE
		SYNTAX 			DisplayString 
		MAX-ACCESS		read-only
		STATUS			current
		DESCRIPTION 
		"
			The manufacture attach to associated with the Disk of this entry.
		"
		::= {nvmeDiskInfoEntry 6}
	 
	nvmeDiskInfoSerialNo  OBJECT-TYPE
		SYNTAX 			DisplayString 
		MAX-ACCESS		read-only
		STATUS			current
		DESCRIPTION 
		"
			The Disk serial number associated with the NvmeDisk of this entry.
		"
		::= {nvmeDiskInfoEntry 7}
		
	nvmeDiskInfoLinkSpeed  OBJECT-TYPE
		SYNTAX 			DisplayString 
		MAX-ACCESS		read-only
		STATUS			current
		DESCRIPTION 
		"
			The linkSpeed associated with the NvmeDisk of this entry.
		"
		::= {nvmeDiskInfoEntry 8}			
		
	nvmeDiskInfoCapacity  OBJECT-TYPE
		SYNTAX 			DisplayString 
		MAX-ACCESS		read-only
		STATUS			current
		DESCRIPTION 
		"
			The capacity associated with the NvmeDisk of this entry.
		"
		::= {nvmeDiskInfoEntry 9}
	nvmeDiskInfoTemp  OBJECT-TYPE
		SYNTAX 			DisplayString 
		MAX-ACCESS		read-only
		STATUS			current
		DESCRIPTION 
		"
			The temp associated with the NvmeDisk of this entry.
		"
		::= {nvmeDiskInfoEntry 10}
					

	nvmeDiskInfoPdlu  OBJECT-TYPE
		SYNTAX 			Integer32
		MAX-ACCESS		read-only
		STATUS			current
		DESCRIPTION 
		"
			The pdlu associated with the NvmeDisk of this entry.
		"
		::= {nvmeDiskInfoEntry 11}
	nvmeDiskInfoStatus  OBJECT-TYPE
		SYNTAX 			Integer32
						{
						 present-nondetected(0),
						 present-detected(1)
						}
		MAX-ACCESS		read-only
		STATUS			current
		DESCRIPTION 
		"
			The status associated with the NvmeDisk of this entry.
		"
		::= {nvmeDiskInfoEntry 12}
--nvmeDiskInfoTable end
--powerInfoTable start
	powerInfoTable	OBJECT-TYPE
	    SYNTAX     SEQUENCE OF PowerInfoEntry
	    MAX-ACCESS read-only
	    STATUS     current
	    DESCRIPTION
	           "The table of information relevant to this entity's power"
			::= {powerUnit 1}
			
	powerInfoEntry OBJECT-TYPE
	    SYNTAX     PowerInfoEntry
	    MAX-ACCESS read-only
	    STATUS     current
	    DESCRIPTION
	           "The information associated with the power of this entry."
	    INDEX   { 
				  powerIndex
	            }
	    ::= { powerInfoTable 1 }   
	
	PowerInfoEntry ::= SEQUENCE {
	  	powerIndex  	Integer32,
	    powerName		DisplayString,
		powerMfr		DisplayString,
		powerType		DisplayString,
		powerModel		DisplayString,
	    powerSerialNo	DisplayString,
		powerVersion	DisplayString,
		ratedPower		DisplayString,
		inputPower		DisplayString,
		outputPower		DisplayString,
		powerHealth		Integer32,
		powerTemp		DisplayString,
		powerFanSpeed	DisplayString
	   }
	powerIndex  OBJECT-TYPE
		SYNTAX 			Integer32
		MAX-ACCESS		read-only
		STATUS			current
		DESCRIPTION 
		"
			The index associated with the power.
		"
		::= {powerInfoEntry 1}
	powerName  OBJECT-TYPE
		SYNTAX 			DisplayString
		MAX-ACCESS		read-only
		STATUS			current
		DESCRIPTION 
		"
			The name associated with the power.
		"
		::= {powerInfoEntry 2}
	powerMfr  OBJECT-TYPE
		SYNTAX 			DisplayString
		MAX-ACCESS		read-only
		STATUS			current
		DESCRIPTION 
		"
			The manufacturer associated with the power.
		"
		::= {powerInfoEntry 3}
	powerType  OBJECT-TYPE
		SYNTAX 			DisplayString
		MAX-ACCESS		read-only
		STATUS			current
		DESCRIPTION 
		"
			The Power Type associated with the power.
		"
		::= {powerInfoEntry 4}
	powerModel  OBJECT-TYPE
		SYNTAX 			DisplayString
		MAX-ACCESS		read-only
		STATUS			current
		DESCRIPTION 
		"
			The model num associated with the power.
		"
		::= {powerInfoEntry 5}
	powerSerialNo  OBJECT-TYPE
		SYNTAX 			DisplayString
		MAX-ACCESS		read-only
		STATUS			current
		DESCRIPTION 
		"
			The serial num associated with the power.
		"
		::= {powerInfoEntry 6}
	powerVersion  OBJECT-TYPE
		SYNTAX 			DisplayString
		MAX-ACCESS		read-only
		STATUS			current
		DESCRIPTION 
		"
			The version associated with the power.
		"
		::= {powerInfoEntry 7}
	ratedPower  OBJECT-TYPE
		SYNTAX 			DisplayString
		MAX-ACCESS		read-only
		STATUS			current
		DESCRIPTION 
		"
			The rated power associated with the power.
		"
		::= {powerInfoEntry 8}
	inputPower  OBJECT-TYPE
		SYNTAX 			DisplayString
		MAX-ACCESS		read-only
		STATUS			current
		DESCRIPTION 
		"
			The input power associated with the power.
		"
		::= {powerInfoEntry 9}
	outputPower  OBJECT-TYPE
		SYNTAX 			DisplayString
		MAX-ACCESS		read-only
		STATUS			current
		DESCRIPTION 
		"
			The output power associated with the power.
		"
		::= {powerInfoEntry 10}
	powerHealth  OBJECT-TYPE
		SYNTAX 			Integer32 { normal(0), abnormal(1), absent(2) }
		MAX-ACCESS		read-only
		STATUS			current
		DESCRIPTION 
		"
			The health state associated with the power.
		"
		::= {powerInfoEntry 11}
	powerTemp  OBJECT-TYPE
		SYNTAX 			DisplayString
		MAX-ACCESS		read-only
		STATUS			current
		DESCRIPTION 
		"
			The temprature associated with the power unit.
		"
		::= {powerInfoEntry 12}
	powerFanSpeed  OBJECT-TYPE
		SYNTAX 			DisplayString
		MAX-ACCESS		read-only
		STATUS			current
		DESCRIPTION 
		"
			The psu fan speed associated with the power unit.
		"
		::= {powerInfoEntry 13}
--powerInfoTable end

--nmPolicyInfoTable start
	nmPolicyInfoTable	OBJECT-TYPE
	    SYNTAX     SEQUENCE OF NmPolicyInfoEntry
	    MAX-ACCESS read-only
	    STATUS     current
	    DESCRIPTION
	           "The table of information relevant to this entity's nmPolicy"
			::= {powerUnit 2}
			
	nmPolicyInfoEntry OBJECT-TYPE
	    SYNTAX     NmPolicyInfoEntry 
	    MAX-ACCESS read-only
	    STATUS     current
	    DESCRIPTION
	           "The information associated with the nmPolicy of this entry."
	    INDEX   { 
				  nmPolicyIndex
	            }
	    ::= { nmPolicyInfoTable 1 }   
	
	NmPolicyInfoEntry ::= SEQUENCE {
	  	nmPolicyIndex  				Integer32,
	    nmPolicyDomainName			DisplayString,
		nmPolicyCurrentPower		Integer32,
		nmPolicyCurrentPower		Integer32,
		nmPolicyMaxPower			Integer32,
		nmPolicyPowerCappingStatus	Integer32,
	    nmPolicyPowerLimitValue		Integer32,
		nmPolicyShutDown			Integer32,
		nmPolicyAlert				Integer32
	   }
	nmPolicyIndex  OBJECT-TYPE
		SYNTAX 			Integer32
		MAX-ACCESS		read-only
		STATUS			current
		DESCRIPTION 
		"
			The index associated with the nmPolicy.
		"
		::= {nmPolicyInfoEntry 1}
	nmPolicyDomainName  OBJECT-TYPE
		SYNTAX 			DisplayString
		MAX-ACCESS		read-only
		STATUS			current
		DESCRIPTION 
		"
			The Domain name associated with the nmPolicy.
		"
		::= {nmPolicyInfoEntry 2}
	nmPolicyCurrentPower  OBJECT-TYPE
		SYNTAX 			Integer32
		MAX-ACCESS		read-only
		STATUS			current
		DESCRIPTION 
		"
			The current power associated with the nmPolicy.
		"
		::= {nmPolicyInfoEntry 3}
	nmPolicyMaxPower  OBJECT-TYPE
		SYNTAX 			Integer32
		MAX-ACCESS		read-only
		STATUS			current
		DESCRIPTION 
		"
			The nmPolicy Maximum power associated with the nmPolicy.
		"
		::= {nmPolicyInfoEntry 4}
	nmPolicyPowerCappingStatus  OBJECT-TYPE
		SYNTAX 			Integer32
						{
						 disabled(0),
						 enabled(1)
						}
		MAX-ACCESS		read-write
		STATUS			current
		DESCRIPTION 
		"
			The capping status associated with the nmPolicy.
		"
		::= {nmPolicyInfoEntry 5}
	nmPolicyPowerLimitValue  OBJECT-TYPE
		SYNTAX 			Integer32
		MAX-ACCESS		read-write
		STATUS			current
		DESCRIPTION 
		"
			The Limit Value associated with the nmPolicy.
		"
		::= {nmPolicyInfoEntry 6}
	nmPolicyShutDown  OBJECT-TYPE
		SYNTAX 			Integer32
						{
						 disabled(0),
						 enabled(1)
						}
		MAX-ACCESS		read-write
		STATUS			current
		DESCRIPTION 
		"
			The shutDown associated with the nmPolicy.
		"
		::= {nmPolicyInfoEntry 7}
	nmPolicyAlert  OBJECT-TYPE
		SYNTAX 			Integer32
						{
						 disabled(0),
						 enabled(1)
						}
		MAX-ACCESS		read-write
		STATUS			current
		DESCRIPTION 
		"
			The Alert nmPolicy associated with the nmPolicy.
		"
		::= {nmPolicyInfoEntry 8}
--nmPolicyInfoTable end
--powerCommon start
--	maxPowerConsumptionCap  OBJECT-TYPE
--		SYNTAX 			DisplayString
--		MAX-ACCESS		read-only
--		STATUS			current
--		DESCRIPTION 
--		"
--			The max power consumption of the cap associated with the power.
--		"
--		::= {powerCommon 1}
--	minPowerConsumptionCap  OBJECT-TYPE
--		SYNTAX 			DisplayString
--		MAX-ACCESS		read-only
--		STATUS			current
--		DESCRIPTION 
--		"
--			The min power consumption of the cap's value associated with the power.
--		"
--		::= {powerCommon 2}
--	serverPowerConsumption  OBJECT-TYPE
--		SYNTAX 			DisplayString
--		MAX-ACCESS		read-only
--		STATUS			current
--		DESCRIPTION 
--		"
--			The current server power consumption.
--		"
--		::= {powerCommon 3}
--powerCommon end
--eventLogsTable start
	eventLogsTable	OBJECT-TYPE
	    SYNTAX     SEQUENCE OF EventLogsEntry
	    MAX-ACCESS read-only
	    STATUS     current
	    DESCRIPTION
	           "The table of information relevant to this entity's event logs"
			::= {serverAssetInfo 11}
			
	eventLogsEntry OBJECT-TYPE
	    SYNTAX     EventLogsEntry
	    MAX-ACCESS read-only
	    STATUS     current
	    DESCRIPTION
	           "The information associated with the event logs of this entry."
	    INDEX   { 
				  eventLogsIndex
	            }
	    ::= { eventLogsTable 1 } 
	EventLogsEntry ::= SEQUENCE {
	  	eventLogsIndex  		Integer32,
	    eventLogsEventID		Integer32,
		eventLogsTimeStamp		DisplayString,
		eventLogsSensorName		DisplayString,
		eventLogsSensorType		DisplayString,
		eventLogsDescription	DisplayString,
		eventLogsEventType		DisplayString
	   }
	eventLogsIndex  OBJECT-TYPE
		SYNTAX 			Integer32
		MAX-ACCESS		read-only
		STATUS			current
		DESCRIPTION 
		"
			The index associated with the event logs.
		"
		::= {eventLogsEntry 1}
	eventLogsEventID  OBJECT-TYPE
		SYNTAX 			Integer32
		MAX-ACCESS		read-only
		STATUS			current
		DESCRIPTION 
		"
			The event id associated with the event logs.
		"
		::= {eventLogsEntry 2}
	eventLogsTimeStamp  OBJECT-TYPE
		SYNTAX 			DisplayString
		MAX-ACCESS		read-only
		STATUS			current
		DESCRIPTION 
		"
			The time stamp associated with the event logs.
		"
		::= {eventLogsEntry 3}
	eventLogsSensorName  OBJECT-TYPE
		SYNTAX 			DisplayString
		MAX-ACCESS		read-only
		STATUS			current
		DESCRIPTION 
		"
			The sensor name associated with the event logs.
		"
		::= {eventLogsEntry 4}
	eventLogsSensorType  OBJECT-TYPE
		SYNTAX 			DisplayString
		MAX-ACCESS		read-only
		STATUS			current
		DESCRIPTION 
		"
			The sensor Type associated with the event logs.
		"
		::= {eventLogsEntry 5}
	eventLogsDescription  OBJECT-TYPE
		SYNTAX 			DisplayString
		MAX-ACCESS		read-only
		STATUS			current
		DESCRIPTION 
		"
			The description associated with the event logs.
		"
		::= {eventLogsEntry 6}
	eventLogsEventType  OBJECT-TYPE
		SYNTAX 			DisplayString
		MAX-ACCESS		read-only
		STATUS			current
		DESCRIPTION 
		"
			The event type associated with the event logs.
		"
		::= {eventLogsEntry 7}
--eventLogsTable end
--fanSensorTable start
	fanSensorTable OBJECT-TYPE
		SYNTAX SEQUENCE OF FanSensorEntry
		MAX-ACCESS not-accessible
		STATUS current
		DESCRIPTION
			""
		::= { serverAssetInfo 12 }
	fanSensorEntry OBJECT-TYPE
		SYNTAX FanSensorEntry
		MAX-ACCESS not-accessible
		STATUS current
		DESCRIPTION
			""
		INDEX { fanSensorIndex }
		::= { fanSensorTable 1 }
	FanSensorEntry ::=
		SEQUENCE {
			fanSensorIndex		Integer32,
			fanSensorName		DisplayString,
			fanSensorStatus		DisplayString,
			fanSensorValue		DisplayString,
			fanSensorLowNRT		DisplayString,
			fanSensorLowCT		DisplayString,
			fanSensorLowNCT		DisplayString,
			fanSensorUpNCT		DisplayString,
			fanSensorUpCT		DisplayString,
			fanSensorUpNRT		DisplayString
		}
	fanSensorIndex OBJECT-TYPE
		SYNTAX Integer32
		MAX-ACCESS read-only
		STATUS current
		DESCRIPTION
			""
		::= { fanSensorEntry 1 }
	fanSensorName OBJECT-TYPE
		SYNTAX DisplayString
		MAX-ACCESS read-only
		STATUS current
		DESCRIPTION
			""
		::= { fanSensorEntry 2 }
	fanSensorStatus OBJECT-TYPE
		SYNTAX 			DisplayString
		MAX-ACCESS		read-only
		STATUS			current
		DESCRIPTION 
		"
			The sensor status associated with the fan sensor of this entry.
		"
		::= {fanSensorEntry 3} 
	fanSensorValue OBJECT-TYPE
		SYNTAX DisplayString
		MAX-ACCESS read-only
		STATUS current
		DESCRIPTION
			""
		::= { fanSensorEntry 4 }		
	fanSensorLowNRT OBJECT-TYPE
		SYNTAX 			DisplayString 
		MAX-ACCESS		read-only
		STATUS			current
		DESCRIPTION 
		"
			The lower non-recoverable threshold associated with the fan sensor of this entry.
		"
		::= {fanSensorEntry 5}   
				  
	fanSensorLowCT OBJECT-TYPE
		SYNTAX 			DisplayString
		MAX-ACCESS		read-only
		STATUS			current
		DESCRIPTION 
		"
			The lower critical threshold associated with the fan sensor of this entry.
		"
		::= {fanSensorEntry 6}
	      		  
	fanSensorLowNCT OBJECT-TYPE
		SYNTAX 			DisplayString 
		MAX-ACCESS		read-only
		STATUS			current
		DESCRIPTION 
		"
			The lower non-critical threshold associated with the fan sensor of this entry.
		"
		::= {fanSensorEntry 7}
			  
	fanSensorUpNCT OBJECT-TYPE
		SYNTAX 			DisplayString 
		MAX-ACCESS		read-only
		STATUS			current
		DESCRIPTION 
		"
			The upper non-critical threshold associated with the fan sensor of this entry.
		"
		::= {fanSensorEntry 8}
	      		  
	fanSensorUpCT OBJECT-TYPE
		SYNTAX 			DisplayString 
		MAX-ACCESS		read-only
		STATUS			current
		DESCRIPTION 
		"
			The upper critical threshold associated with the fan sensor of this entry.
		"
		::= {fanSensorEntry 9}
		  
	fanSensorUpNRT OBJECT-TYPE
		SYNTAX 			DisplayString 
		MAX-ACCESS		read-only
		STATUS			current
		DESCRIPTION 
		"
			The upper non-recoverable threshold associated with the fan sensor of this entry.
		"
		::= {fanSensorEntry 10}		
--fanSensorTable end
--tempSensorTable start
	tempSensorTable OBJECT-TYPE
		SYNTAX SEQUENCE OF TempSensorEntry
		MAX-ACCESS not-accessible
		STATUS current
		DESCRIPTION
			""
		::= { serverAssetInfo 13 }
	tempSensorEntry OBJECT-TYPE
		SYNTAX TempSensorEntry
		MAX-ACCESS not-accessible
		STATUS current
		DESCRIPTION
			""
		INDEX { tempSensorIndex }
		::= { tempSensorTable 1 }
	TempSensorEntry ::=
		SEQUENCE {
			tempSensorIndex		Integer32,
			tempSensorName		DisplayString,
			tempSensorStatus	DisplayString,
			tempSensorValue		DisplayString,
			tempSensorLowNRT	DisplayString,
			tempSensorLowCT		DisplayString,
			tempSensorLowNCT	DisplayString,
			tempSensorUpNCT		DisplayString,
			tempSensorUpCT		DisplayString,
			tempSensorUpNRT		DisplayString
		}
	tempSensorIndex OBJECT-TYPE
		SYNTAX Integer32
		MAX-ACCESS read-only
		STATUS current
		DESCRIPTION
			""
		::= { tempSensorEntry 1 }
	tempSensorName OBJECT-TYPE
		SYNTAX DisplayString
		MAX-ACCESS read-only
		STATUS current
		DESCRIPTION
			""
		::= { tempSensorEntry 2 }
	tempSensorStatus OBJECT-TYPE
		SYNTAX 			DisplayString
		MAX-ACCESS		read-only
		STATUS			current
		DESCRIPTION 
		"
			The sensor status associated with the temp sensor of this entry.
		"
		::= {tempSensorEntry 3} 
	tempSensorValue OBJECT-TYPE
		SYNTAX DisplayString
		MAX-ACCESS read-only
		STATUS current
		DESCRIPTION
			""
		::= { tempSensorEntry 4 }		
	tempSensorLowNRT OBJECT-TYPE
		SYNTAX 			DisplayString 
		MAX-ACCESS		read-only
		STATUS			current
		DESCRIPTION 
		"
			The lower non-recoverable threshold associated with the temp sensor of this entry.
		"
		::= {tempSensorEntry 5}   
				  
	tempSensorLowCT OBJECT-TYPE
		SYNTAX 			DisplayString
		MAX-ACCESS		read-only
		STATUS			current
		DESCRIPTION 
		"
			The lower critical threshold associated with the temp sensor of this entry.
		"
		::= {tempSensorEntry 6}
	      		  
	tempSensorLowNCT OBJECT-TYPE
		SYNTAX 			DisplayString 
		MAX-ACCESS		read-only
		STATUS			current
		DESCRIPTION 
		"
			The lower non-critical threshold associated with the temp sensor of this entry.
		"
		::= {tempSensorEntry 7}
			  
	tempSensorUpNCT OBJECT-TYPE
		SYNTAX 			DisplayString 
		MAX-ACCESS		read-only
		STATUS			current
		DESCRIPTION 
		"
			The upper non-critical threshold associated with the temp sensor of this entry.
		"
		::= {tempSensorEntry 8}
	      		  
	tempSensorUpCT OBJECT-TYPE
		SYNTAX 			DisplayString 
		MAX-ACCESS		read-only
		STATUS			current
		DESCRIPTION 
		"
			The upper critical threshold associated with the temp sensor of this entry.
		"
		::= {tempSensorEntry 9}
		  
	tempSensorUpNRT OBJECT-TYPE
		SYNTAX 			DisplayString 
		MAX-ACCESS		read-only
		STATUS			current
		DESCRIPTION 
		"
			The upper non-recoverable threshold associated with the temp sensor of this entry.
		"
		::= {tempSensorEntry 10}	
--tempSensorTable end
--voltageSensorTable start
	voltageSensorTable OBJECT-TYPE
		SYNTAX SEQUENCE OF VoltageSensorEntry
		MAX-ACCESS not-accessible
		STATUS current
		DESCRIPTION
			""
		::= { serverAssetInfo 14 }
	voltageSensorEntry OBJECT-TYPE
		SYNTAX VoltageSensorEntry
		MAX-ACCESS not-accessible
		STATUS current
		DESCRIPTION
			""
		INDEX { voltageSensorIndex }
		::= { voltageSensorTable 1 }
	VoltageSensorEntry ::=
		SEQUENCE {
			voltageSensorIndex		Integer32,
			voltageSensorName		DisplayString,
			voltageSensorStatus		DisplayString,
			voltageSensorValue		DisplayString,
			voltageSensorLowNRT		DisplayString,
			voltageSensorLowCT		DisplayString,
			voltageSensorLowNCT		DisplayString,
			voltageSensorUpNCT		DisplayString,
			voltageSensorUpCT		DisplayString,
			voltageSensorUpNRT		DisplayString
		}
	voltageSensorIndex OBJECT-TYPE
		SYNTAX Integer32
		MAX-ACCESS read-only
		STATUS current
		DESCRIPTION
			""
		::= { voltageSensorEntry 1 }
	voltageSensorName OBJECT-TYPE
		SYNTAX DisplayString
		MAX-ACCESS read-only
		STATUS current
		DESCRIPTION
			""
		::= { voltageSensorEntry 2 }
	voltageSensorStatus OBJECT-TYPE
		SYNTAX 			DisplayString
		MAX-ACCESS		read-only
		STATUS			current
		DESCRIPTION 
		"
			The sensor status associated with the voltage sensor of this entry.
		"
		::= {voltageSensorEntry 3} 
	voltageSensorValue OBJECT-TYPE
		SYNTAX DisplayString
		MAX-ACCESS read-only
		STATUS current
		DESCRIPTION
			""
		::= { voltageSensorEntry 4 }		
	voltageSensorLowNRT OBJECT-TYPE
		SYNTAX 			DisplayString 
		MAX-ACCESS		read-only
		STATUS			current
		DESCRIPTION 
		"
			The lower non-recoverable threshold associated with the voltage sensor of this entry.
		"
		::= {voltageSensorEntry 5}   
				  
	voltageSensorLowCT OBJECT-TYPE
		SYNTAX 			DisplayString
		MAX-ACCESS		read-only
		STATUS			current
		DESCRIPTION 
		"
			The lower critical threshold associated with the voltage sensor of this entry.
		"
		::= {voltageSensorEntry 6}
	      		  
	voltageSensorLowNCT OBJECT-TYPE
		SYNTAX 			DisplayString 
		MAX-ACCESS		read-only
		STATUS			current
		DESCRIPTION 
		"
			The lower non-critical threshold associated with the voltage sensor of this entry.
		"
		::= {voltageSensorEntry 7}
			  
	voltageSensorUpNCT OBJECT-TYPE
		SYNTAX 			DisplayString 
		MAX-ACCESS		read-only
		STATUS			current
		DESCRIPTION 
		"
			The upper non-critical threshold associated with the voltage sensor of this entry.
		"
		::= {voltageSensorEntry 8}
	      		  
	voltageSensorUpCT OBJECT-TYPE
		SYNTAX 			DisplayString 
		MAX-ACCESS		read-only
		STATUS			current
		DESCRIPTION 
		"
			The upper critical threshold associated with the voltage sensor of this entry.
		"
		::= {voltageSensorEntry 9}
		  
	voltageSensorUpNRT OBJECT-TYPE
		SYNTAX 			DisplayString 
		MAX-ACCESS		read-only
		STATUS			current
		DESCRIPTION 
		"
			The upper non-recoverable threshold associated with the voltage sensor of this entry.
		"
		::= {voltageSensorEntry 10}			
--voltageSensorTable end
--currentSensorTable start		
	currentSensorTable OBJECT-TYPE
		SYNTAX SEQUENCE OF CurrentSensorEntry
		MAX-ACCESS not-accessible
		STATUS current
		DESCRIPTION
			""
		::= { serverAssetInfo 15 }
	currentSensorEntry OBJECT-TYPE
		SYNTAX CurrentSensorEntry
		MAX-ACCESS not-accessible
		STATUS current
		DESCRIPTION
			""
		INDEX { currentSensorIndex }
		::= { currentSensorTable 1 }
	CurrentSensorEntry ::=
		SEQUENCE {
			currentSensorIndex		Integer32,
			currentSensorName		DisplayString,
			currentSensorStatus		DisplayString,
			currentSensorValue		DisplayString,
			currentSensorLowNRT		DisplayString,
			currentSensorLowCT		DisplayString,
			currentSensorLowNCT		DisplayString,
			currentSensorUpNCT		DisplayString,
			currentSensorUpCT		DisplayString,
			currentSensorUpNRT		DisplayString
		}
	currentSensorIndex OBJECT-TYPE
		SYNTAX Integer32
		MAX-ACCESS read-only
		STATUS current
		DESCRIPTION
			""
		::= { currentSensorEntry 1 }
	currentSensorName OBJECT-TYPE
		SYNTAX DisplayString
		MAX-ACCESS read-only
		STATUS current
		DESCRIPTION
			""
		::= { currentSensorEntry 2 }
	currentSensorStatus OBJECT-TYPE
		SYNTAX 			DisplayString
		MAX-ACCESS		read-only
		STATUS			current
		DESCRIPTION 
		"
			The sensor status associated with the current sensor of this entry.
		"
		::= {currentSensorEntry 3} 
	currentSensorValue OBJECT-TYPE
		SYNTAX DisplayString
		MAX-ACCESS read-only
		STATUS current
		DESCRIPTION
			""
		::= { currentSensorEntry 4 }		
	currentSensorLowNRT OBJECT-TYPE
		SYNTAX 			DisplayString 
		MAX-ACCESS		read-only
		STATUS			current
		DESCRIPTION 
		"
			The lower non-recoverable threshold associated with the current sensor of this entry.
		"
		::= {currentSensorEntry 5}   
				  
	currentSensorLowCT OBJECT-TYPE
		SYNTAX 			DisplayString
		MAX-ACCESS		read-only
		STATUS			current
		DESCRIPTION 
		"
			The lower critical threshold associated with the current sensor of this entry.
		"
		::= {currentSensorEntry 6}
	      		  
	currentSensorLowNCT OBJECT-TYPE
		SYNTAX 			DisplayString 
		MAX-ACCESS		read-only
		STATUS			current
		DESCRIPTION 
		"
			The lower non-critical threshold associated with the current sensor of this entry.
		"
		::= {currentSensorEntry 7}
			  
	currentSensorUpNCT OBJECT-TYPE
		SYNTAX 			DisplayString 
		MAX-ACCESS		read-only
		STATUS			current
		DESCRIPTION 
		"
			The upper non-critical threshold associated with the current sensor of this entry.
		"
		::= {currentSensorEntry 8}
	      		  
	currentSensorUpCT OBJECT-TYPE
		SYNTAX 			DisplayString 
		MAX-ACCESS		read-only
		STATUS			current
		DESCRIPTION 
		"
			The upper critical threshold associated with the current sensor of this entry.
		"
		::= {currentSensorEntry 9}
		  
	currentSensorUpNRT OBJECT-TYPE
		SYNTAX 			DisplayString 
		MAX-ACCESS		read-only
		STATUS			current
		DESCRIPTION 
		"
			The upper non-recoverable threshold associated with the current sensor of this entry.
		"
		::= {currentSensorEntry 10}			
--currentSensorTable end
--cpuStatusSensorTable start		
	cpuStatusSensorTable OBJECT-TYPE
		SYNTAX SEQUENCE OF CpuStatusSensorEntry
		MAX-ACCESS not-accessible
		STATUS current
		DESCRIPTION
			""
		::= { serverAssetInfo 16 }
	cpuStatusSensorEntry OBJECT-TYPE
		SYNTAX CpuStatusSensorEntry
		MAX-ACCESS not-accessible
		STATUS current
		DESCRIPTION
			""
		INDEX { cpuStatusSensorIndex }
		::= { cpuStatusSensorTable 1 }
	CpuStatusSensorEntry ::=
		SEQUENCE {
			cpuStatusSensorIndex		Integer32,
			cpuStatusSensorName			DisplayString,
			cpuStatusSensorStatus		DisplayString,
			cpuStatusSensorValue		DisplayString,
			cpuStatusSensorLowNRT		DisplayString,
			cpuStatusSensorLowCT		DisplayString,
			cpuStatusSensorLowNCT		DisplayString,
			cpuStatusSensorUpNCT		DisplayString,
			cpuStatusSensorUpCT			DisplayString,
			cpuStatusSensorUpNRT		DisplayString
		}
	cpuStatusSensorIndex OBJECT-TYPE
		SYNTAX Integer32
		MAX-ACCESS read-only
		STATUS current
		DESCRIPTION
			""
		::= { cpuStatusSensorEntry 1 }
	cpuStatusSensorName OBJECT-TYPE
		SYNTAX DisplayString
		MAX-ACCESS read-only
		STATUS current
		DESCRIPTION
			""
		::= { cpuStatusSensorEntry 2 }
	cpuStatusSensorStatus OBJECT-TYPE
		SYNTAX 			DisplayString
		MAX-ACCESS		read-only
		STATUS			current
		DESCRIPTION 
		"
			The sensor status associated with the cpuStatus sensor of this entry.
		"
		::= {cpuStatusSensorEntry 3} 
	cpuStatusSensorValue OBJECT-TYPE
		SYNTAX DisplayString
		MAX-ACCESS read-only
		STATUS current
		DESCRIPTION
			""
		::= { cpuStatusSensorEntry 4 }		
	cpuStatusSensorLowNRT OBJECT-TYPE
		SYNTAX 			DisplayString 
		MAX-ACCESS		read-only
		STATUS			current
		DESCRIPTION 
		"
			The lower non-recoverable threshold associated with the cpuStatus sensor of this entry.
		"
		::= {cpuStatusSensorEntry 5}   
				  
	cpuStatusSensorLowCT OBJECT-TYPE
		SYNTAX 			DisplayString
		MAX-ACCESS		read-only
		STATUS			current
		DESCRIPTION 
		"
			The lower critical threshold associated with the cpuStatus sensor of this entry.
		"
		::= {cpuStatusSensorEntry 6}
	      		  
	cpuStatusSensorLowNCT OBJECT-TYPE
		SYNTAX 			DisplayString 
		MAX-ACCESS		read-only
		STATUS			current
		DESCRIPTION 
		"
			The lower non-critical threshold associated with the cpuStatus sensor of this entry.
		"
		::= {cpuStatusSensorEntry 7}
			  
	cpuStatusSensorUpNCT OBJECT-TYPE
		SYNTAX 			DisplayString 
		MAX-ACCESS		read-only
		STATUS			current
		DESCRIPTION 
		"
			The upper non-critical threshold associated with the cpuStatus sensor of this entry.
		"
		::= {cpuStatusSensorEntry 8}
	      		  
	cpuStatusSensorUpCT OBJECT-TYPE
		SYNTAX 			DisplayString 
		MAX-ACCESS		read-only
		STATUS			current
		DESCRIPTION 
		"
			The upper critical threshold associated with the cpuStatus sensor of this entry.
		"
		::= {cpuStatusSensorEntry 9}
		  
	cpuStatusSensorUpNRT OBJECT-TYPE
		SYNTAX 			DisplayString 
		MAX-ACCESS		read-only
		STATUS			current
		DESCRIPTION 
		"
			The upper non-recoverable threshold associated with the cpuStatus sensor of this entry.
		"
		::= {cpuStatusSensorEntry 10}			
--cpuStatusSensorTable end
--powerSupplySensorTable start
	powerSupplySensorTable OBJECT-TYPE
		SYNTAX SEQUENCE OF PowerSupplySensorEntry
		MAX-ACCESS not-accessible
		STATUS current
		DESCRIPTION
			""
		::= { serverAssetInfo 17 }
	powerSupplySensorEntry OBJECT-TYPE
		SYNTAX PowerSupplySensorEntry
		MAX-ACCESS not-accessible
		STATUS current
		DESCRIPTION
			""
		INDEX { powerSupplySensorIndex }
		::= { powerSupplySensorTable 1 }
	PowerSupplySensorEntry ::=
		SEQUENCE {
			powerSupplySensorIndex		Integer32,
			powerSupplySensorName		DisplayString,
			powerSupplySensorStatus		DisplayString,
			powerSupplySensorValue		DisplayString,
			powerSupplySensorLowNRT		DisplayString,
			powerSupplySensorLowCT		DisplayString,
			powerSupplySensorLowNCT		DisplayString,
			powerSupplySensorUpNCT		DisplayString,
			powerSupplySensorUpCT		DisplayString,
			powerSupplySensorUpNRT		DisplayString
		}
	powerSupplySensorIndex OBJECT-TYPE
		SYNTAX Integer32
		MAX-ACCESS read-only
		STATUS current
		DESCRIPTION
			""
		::= { powerSupplySensorEntry 1 }
	powerSupplySensorName OBJECT-TYPE
		SYNTAX DisplayString
		MAX-ACCESS read-only
		STATUS current
		DESCRIPTION
			""
		::= { powerSupplySensorEntry 2 }
	powerSupplySensorStatus OBJECT-TYPE
		SYNTAX 			DisplayString
		MAX-ACCESS		read-only
		STATUS			current
		DESCRIPTION 
		"
			The sensor status associated with the powerSupply sensor of this entry.
		"
		::= {powerSupplySensorEntry 3} 
	powerSupplySensorValue OBJECT-TYPE
		SYNTAX DisplayString
		MAX-ACCESS read-only
		STATUS current
		DESCRIPTION
			""
		::= { powerSupplySensorEntry 4 }		
	powerSupplySensorLowNRT OBJECT-TYPE
		SYNTAX 			DisplayString 
		MAX-ACCESS		read-only
		STATUS			current
		DESCRIPTION 
		"
			The lower non-recoverable threshold associated with the powerSupply sensor of this entry.
		"
		::= {powerSupplySensorEntry 5}   
				  
	powerSupplySensorLowCT OBJECT-TYPE
		SYNTAX 			DisplayString
		MAX-ACCESS		read-only
		STATUS			current
		DESCRIPTION 
		"
			The lower critical threshold associated with the powerSupply sensor of this entry.
		"
		::= {powerSupplySensorEntry 6}
	      		  
	powerSupplySensorLowNCT OBJECT-TYPE
		SYNTAX 			DisplayString 
		MAX-ACCESS		read-only
		STATUS			current
		DESCRIPTION 
		"
			The lower non-critical threshold associated with the powerSupply sensor of this entry.
		"
		::= {powerSupplySensorEntry 7}
			  
	powerSupplySensorUpNCT OBJECT-TYPE
		SYNTAX 			DisplayString 
		MAX-ACCESS		read-only
		STATUS			current
		DESCRIPTION 
		"
			The upper non-critical threshold associated with the powerSupply sensor of this entry.
		"
		::= {powerSupplySensorEntry 8}
	      		  
	powerSupplySensorUpCT OBJECT-TYPE
		SYNTAX 			DisplayString 
		MAX-ACCESS		read-only
		STATUS			current
		DESCRIPTION 
		"
			The upper critical threshold associated with the powerSupply sensor of this entry.
		"
		::= {powerSupplySensorEntry 9}
		  
	powerSupplySensorUpNRT OBJECT-TYPE
		SYNTAX 			DisplayString 
		MAX-ACCESS		read-only
		STATUS			current
		DESCRIPTION 
		"
			The upper non-recoverable threshold associated with the powerSupply sensor of this entry.
		"
		::= {powerSupplySensorEntry 10}		
--powerSupplySensorTable end
--powerUnitSensorTable start	
	powerUnitSensorTable OBJECT-TYPE
		SYNTAX SEQUENCE OF PowerUnitSensorEntry
		MAX-ACCESS not-accessible
		STATUS current
		DESCRIPTION
			""
		::= { serverAssetInfo 18 }
	powerUnitSensorEntry OBJECT-TYPE
		SYNTAX PowerUnitSensorEntry
		MAX-ACCESS not-accessible
		STATUS current
		DESCRIPTION
			""
		INDEX { powerUnitSensorIndex }
		::= { powerUnitSensorTable 1 }
	PowerUnitSensorEntry ::=
		SEQUENCE {
			powerUnitSensorIndex		Integer32,
			powerUnitSensorName			DisplayString,
			powerUnitSensorStatus		DisplayString,
			powerUnitSensorValue		DisplayString,
			powerUnitSensorLowNRT		DisplayString,
			powerUnitSensorLowCT		DisplayString,
			powerUnitSensorLowNCT		DisplayString,
			powerUnitSensorUpNCT		DisplayString,
			powerUnitSensorUpCT			DisplayString,
			powerUnitSensorUpNRT		DisplayString
		}
	powerUnitSensorIndex OBJECT-TYPE
		SYNTAX Integer32
		MAX-ACCESS read-only
		STATUS current
		DESCRIPTION
			""
		::= { powerUnitSensorEntry 1 }
	powerUnitSensorName OBJECT-TYPE
		SYNTAX DisplayString
		MAX-ACCESS read-only
		STATUS current
		DESCRIPTION
			""
		::= { powerUnitSensorEntry 2 }
	powerUnitSensorStatus OBJECT-TYPE
		SYNTAX 			DisplayString
		MAX-ACCESS		read-only
		STATUS			current
		DESCRIPTION 
		"
			The sensor status associated with the powerUnit sensor of this entry.
		"
		::= {powerUnitSensorEntry 3} 
	powerUnitSensorValue OBJECT-TYPE
		SYNTAX DisplayString
		MAX-ACCESS read-only
		STATUS current
		DESCRIPTION
			""
		::= { powerUnitSensorEntry 4 }		
	powerUnitSensorLowNRT OBJECT-TYPE
		SYNTAX 			DisplayString 
		MAX-ACCESS		read-only
		STATUS			current
		DESCRIPTION 
		"
			The lower non-recoverable threshold associated with the powerUnit sensor of this entry.
		"
		::= {powerUnitSensorEntry 5}   
				  
	powerUnitSensorLowCT OBJECT-TYPE
		SYNTAX 			DisplayString
		MAX-ACCESS		read-only
		STATUS			current
		DESCRIPTION 
		"
			The lower critical threshold associated with the powerUnit sensor of this entry.
		"
		::= {powerUnitSensorEntry 6}
	      		  
	powerUnitSensorLowNCT OBJECT-TYPE
		SYNTAX 			DisplayString 
		MAX-ACCESS		read-only
		STATUS			current
		DESCRIPTION 
		"
			The lower non-critical threshold associated with the powerUnit sensor of this entry.
		"
		::= {powerUnitSensorEntry 7}
			  
	powerUnitSensorUpNCT OBJECT-TYPE
		SYNTAX 			DisplayString 
		MAX-ACCESS		read-only
		STATUS			current
		DESCRIPTION 
		"
			The upper non-critical threshold associated with the powerUnit sensor of this entry.
		"
		::= {powerUnitSensorEntry 8}
	      		  
	powerUnitSensorUpCT OBJECT-TYPE
		SYNTAX 			DisplayString 
		MAX-ACCESS		read-only
		STATUS			current
		DESCRIPTION 
		"
			The upper critical threshold associated with the powerUnit sensor of this entry.
		"
		::= {powerUnitSensorEntry 9}
		  
	powerUnitSensorUpNRT OBJECT-TYPE
		SYNTAX 			DisplayString 
		MAX-ACCESS		read-only
		STATUS			current
		DESCRIPTION 
		"
			The upper non-recoverable threshold associated with the powerUnit sensor of this entry.
		"
		::= {powerUnitSensorEntry 10}	
--powerUnitSensorTable end
--otherSensorTable start
	otherSensorTable OBJECT-TYPE
		SYNTAX SEQUENCE OF OtherSensorEntry
		MAX-ACCESS not-accessible
		STATUS current
		DESCRIPTION
			""
		::= { serverAssetInfo 19 }
	otherSensorEntry OBJECT-TYPE
		SYNTAX OtherSensorEntry
		MAX-ACCESS not-accessible
		STATUS current
		DESCRIPTION
			""
		INDEX { otherSensorIndex }
		::= { otherSensorTable 1 }
	OtherSensorEntry ::=
		SEQUENCE {
			otherSensorIndex		Integer32,
			otherSensorName		DisplayString,
			otherSensorStatus		DisplayString,
			otherSensorValue		DisplayString,
			otherSensorLowNRT		DisplayString,
			otherSensorLowCT		DisplayString,
			otherSensorLowNCT		DisplayString,
			otherSensorUpNCT		DisplayString,
			otherSensorUpCT		DisplayString,
			otherSensorUpNRT		DisplayString
		}
	otherSensorIndex OBJECT-TYPE
		SYNTAX Integer32
		MAX-ACCESS read-only
		STATUS current
		DESCRIPTION
			""
		::= { otherSensorEntry 1 }
	otherSensorName OBJECT-TYPE
		SYNTAX DisplayString
		MAX-ACCESS read-only
		STATUS current
		DESCRIPTION
			""
		::= { otherSensorEntry 2 }
	otherSensorStatus OBJECT-TYPE
		SYNTAX 			DisplayString
		MAX-ACCESS		read-only
		STATUS			current
		DESCRIPTION 
		"
			The sensor status associated with the other sensor of this entry.
		"
		::= {otherSensorEntry 3} 
	otherSensorValue OBJECT-TYPE
		SYNTAX DisplayString
		MAX-ACCESS read-only
		STATUS current
		DESCRIPTION
			""
		::= { otherSensorEntry 4 }		
	otherSensorLowNRT OBJECT-TYPE
		SYNTAX 			DisplayString 
		MAX-ACCESS		read-only
		STATUS			current
		DESCRIPTION 
		"
			The lower non-recoverable threshold associated with the other sensor of this entry.
		"
		::= {otherSensorEntry 5}   
				  
	otherSensorLowCT OBJECT-TYPE
		SYNTAX 			DisplayString
		MAX-ACCESS		read-only
		STATUS			current
		DESCRIPTION 
		"
			The lower critical threshold associated with the other sensor of this entry.
		"
		::= {otherSensorEntry 6}
	      		  
	otherSensorLowNCT OBJECT-TYPE
		SYNTAX 			DisplayString 
		MAX-ACCESS		read-only
		STATUS			current
		DESCRIPTION 
		"
			The lower non-critical threshold associated with the other sensor of this entry.
		"
		::= {otherSensorEntry 7}
			  
	otherSensorUpNCT OBJECT-TYPE
		SYNTAX 			DisplayString 
		MAX-ACCESS		read-only
		STATUS			current
		DESCRIPTION 
		"
			The upper non-critical threshold associated with the other sensor of this entry.
		"
		::= {otherSensorEntry 8}
	      		  
	otherSensorUpCT OBJECT-TYPE
		SYNTAX 			DisplayString 
		MAX-ACCESS		read-only
		STATUS			current
		DESCRIPTION 
		"
			The upper critical threshold associated with the other sensor of this entry.
		"
		::= {otherSensorEntry 9}
		  
	otherSensorUpNRT OBJECT-TYPE
		SYNTAX 			DisplayString 
		MAX-ACCESS		read-only
		STATUS			current
		DESCRIPTION 
		"
			The upper non-recoverable threshold associated with the other sensor of this entry.
		"
		::= {otherSensorEntry 10}	
--otherSensorTable end
--raidControllerInfoTable start
	raidControllerInfoTable	OBJECT-TYPE
	    SYNTAX     SEQUENCE OF RaidControllerInfoEntry
	    MAX-ACCESS read-only
	    STATUS     current
	    DESCRIPTION
	           "The table of Raid Controllor information relevant to this entity's Raid"
	 	::= {serverAssetInfo 20}  
	 
	raidControllerInfoEntry OBJECT-TYPE
	    SYNTAX     RaidControllerInfoEntry
	    MAX-ACCESS read-only
	    STATUS     current
	    DESCRIPTION
	           "The RaidControllor information for one of this entity's Raid."
	    INDEX   { 
				  raidControllerInfoIndex
	            }
	    ::= { raidControllerInfoTable 1 }   
	
	RaidControllerInfoEntry ::= 
	SEQUENCE {
	    raidControllerInfoIndex     		Integer32,
	    raidControllerInfoName				DisplayString,
		raidControllerInfoSerialNumber		DisplayString,
		raidControllerInfoPackageVersion	DisplayString,
		raidControllerInfoFirmwareVersion	DisplayString,
		raidControllerInfoBIOSVersion		DisplayString,
--		raidControllerInfoUEFIVersion		DisplayString,
		raidControllerInfoExpanderVersion	DisplayString,
		raidControllerInfoNVDATAVersion		DisplayString,
		raidControllerInfoCPLDVersion		DisplayString,
		raidControllerInfoPCIVendorID		DisplayString,
		raidControllerInfoPCIDeviceID		DisplayString,
		raidControllerInfoPCISubVendorID	DisplayString,
		raidControllerInfoPCISubSystemID	DisplayString,
		raidControllerInfoROCTemp			DisplayString,
		raidControllerInfoSpeed				DisplayString,
--		raidControllerInfoJbodMode			DisplayString,
		raidControllerInfoExpanderTemp		DisplayString,
		raidControllerInfoTMMSize			DisplayString
--		raidControllerInfoRaidStatus		DisplayString
	}		
	raidControllerInfoIndex  OBJECT-TYPE
		SYNTAX 			Integer32
		MAX-ACCESS		read-only
		STATUS			current
		DESCRIPTION 
		"
			The index value which uniquely identifies the interface to which this entry is applicable.
		"
		::= {raidControllerInfoEntry 1}
	raidControllerInfoName  OBJECT-TYPE
		SYNTAX 			DisplayString
		MAX-ACCESS		read-only
		STATUS			current
		DESCRIPTION 
		"
			The Raid name associated with the Raid of this entry .
		"
		::= {raidControllerInfoEntry 2} 
	raidControllerInfoSerialNumber  OBJECT-TYPE
		SYNTAX 			DisplayString
		MAX-ACCESS		read-only
		STATUS			current
		DESCRIPTION 
		"
			The serial number associated with the Raid of this entry .
		"
		::= {raidControllerInfoEntry 3}		
	raidControllerInfoPackageVersion  OBJECT-TYPE
		SYNTAX 			DisplayString
		MAX-ACCESS		read-only
		STATUS			current
		DESCRIPTION 
		"
			The package version associated with the Raid of this entry .
		"
		::= {raidControllerInfoEntry 4}
	raidControllerInfoFirmwareVersion  OBJECT-TYPE
		SYNTAX 			DisplayString
		MAX-ACCESS		read-only
		STATUS			current
		DESCRIPTION 
		"
			The Firmware version associated with the Raid of this entry .
		"
		::= {raidControllerInfoEntry 5}
	raidControllerInfoBIOSVersion  OBJECT-TYPE
		SYNTAX 			DisplayString
		MAX-ACCESS		read-only
		STATUS			current
		DESCRIPTION 
		"
			The bios version associated with the Raid of this entry .
		"
		::= {raidControllerInfoEntry 6}
--	raidControllerInfoUEFIVersion  OBJECT-TYPE
--		SYNTAX 			DisplayString
--		MAX-ACCESS		read-only
--		STATUS			current
--		DESCRIPTION 
--		"
--			The uefi version associated with the Raid of this entry .
--		"
--		::= {raidControllerInfoEntry 7}
	raidControllerInfoExpanderVersion  OBJECT-TYPE
		SYNTAX 			DisplayString
		MAX-ACCESS		read-only
		STATUS			current
		DESCRIPTION 
		"
			The expander version associated with the Raid of this entry .
		"
		::= {raidControllerInfoEntry 7}
	raidControllerInfoNVDATAVersion  OBJECT-TYPE
		SYNTAX 			DisplayString
		MAX-ACCESS		read-only
		STATUS			current
		DESCRIPTION 
		"
			The seeprom version name associated with the Raid of this entry .
		"
		::= {raidControllerInfoEntry 8}
	raidControllerInfoCPLDVersion  OBJECT-TYPE
		SYNTAX 			DisplayString
		MAX-ACCESS		read-only
		STATUS			current
		DESCRIPTION 
		"
			The cpld version associated with the Raid of this entry .
		"
		::= {raidControllerInfoEntry 9}
	raidControllerInfoPCIVendorID  OBJECT-TYPE
		SYNTAX 			DisplayString
		MAX-ACCESS		read-only
		STATUS			current
		DESCRIPTION 
		"
			The pci vendor id associated with the Raid of this entry .
		"
		::= {raidControllerInfoEntry 10}
	raidControllerInfoPCIDeviceID  OBJECT-TYPE
		SYNTAX 			DisplayString
		MAX-ACCESS		read-only
		STATUS			current
		DESCRIPTION 
		"
			The pci device id name associated with the Raid of this entry .
		"
		::= {raidControllerInfoEntry 11}
	raidControllerInfoPCISubVendorID  OBJECT-TYPE
		SYNTAX 			DisplayString
		MAX-ACCESS		read-only
		STATUS			current
		DESCRIPTION 
		"
			The pci sub vendor id associated with the Raid of this entry .
		"
		::= {raidControllerInfoEntry 12}
	raidControllerInfoPCISubSystemID  OBJECT-TYPE
		SYNTAX 			DisplayString
		MAX-ACCESS		read-only
		STATUS			current
		DESCRIPTION 
		"
			The pci sub system id associated with the Raid of this entry .
		"
		::= {raidControllerInfoEntry 13}
	raidControllerInfoROCTemp  OBJECT-TYPE
		SYNTAX 			DisplayString
		MAX-ACCESS		read-only
		STATUS			current
		DESCRIPTION 
		"
			The roc temp associated with the Raid of this entry .
		"
		::= {raidControllerInfoEntry 14}
	raidControllerInfoSpeed  OBJECT-TYPE
		SYNTAX 			DisplayString
		MAX-ACCESS		read-only
		STATUS			current
		DESCRIPTION 
		"
			The Speed associated with the Raid of this entry .
		"
		::= {raidControllerInfoEntry 15}
--	raidControllerInfoJbodMode  OBJECT-TYPE
--		SYNTAX 			DisplayString
--		MAX-ACCESS		read-only
--		STATUS			current
--		DESCRIPTION 
--		"
--			The Jbod Mode associated with the Raid of this entry .
--		"
--		::= {raidControllerInfoEntry 17}
	raidControllerInfoExpanderTemp  OBJECT-TYPE
		SYNTAX 			DisplayString
		MAX-ACCESS		read-only
		STATUS			current
		DESCRIPTION 
		"
			The expander temp associated with the Raid of this entry .
		"
		::= {raidControllerInfoEntry 16}
	raidControllerInfoTMMSize  OBJECT-TYPE
		SYNTAX 			DisplayString
		MAX-ACCESS		read-only
		STATUS			current
		DESCRIPTION 
		"
			The tmm size associated with the Raid of this entry .
		"
		::= {raidControllerInfoEntry 17}
--	raidControllerInfoRaidStatus  OBJECT-TYPE
--		SYNTAX 			DisplayString
--		MAX-ACCESS		read-only
--		STATUS			current
--		DESCRIPTION 
--		"
--			The Raid Status associated with the Raid of this entry .
--		"
--		::= {raidControllerInfoEntry 19}
--raidControllerInfoTable end
--raidPhysicalInfoTable start
	raidPhysicalInfoTable	OBJECT-TYPE
	    SYNTAX     SEQUENCE OF RaidPhysicalInfoEntry
	    MAX-ACCESS read-only
	    STATUS     current
	    DESCRIPTION
	           "The table of physical information relevant to this entity's Raid"
	 	::= {serverAssetInfo 21}  
	 
	raidPhysicalInfoEntry OBJECT-TYPE
	    SYNTAX     RaidPhysicalInfoEntry
	    MAX-ACCESS read-only
	    STATUS     current
	    DESCRIPTION
	           "The physical information for one of this entity's Raid."
	    INDEX   { 
				  raidPhysicalInfoIndex
	            }
	    ::= { raidPhysicalInfoTable 1 }   
	
	RaidPhysicalInfoEntry ::= 
	SEQUENCE {
	    raidPhysicalInfoIndex     		Integer32,
		raidPhysicalInfoDeviceID		Integer32,
		raidPhysicalInfoController		DisplayString,
		raidPhysicalInfoMediaType		DisplayString,
		raidPhysicalInfoState			DisplayString,
		raidPhysicalInfoSlot			Integer32,
		raidPhysicalInfoSpeed			DisplayString,
		raidPhysicalInfoLinkSpeed		DisplayString,
		raidPhysicalInfoSize			DisplayString,
		raidPhysicalInfoTemp			DisplayString,
--		raidPhysicalInfoLocateStatus	DisplayString,
		raidPhysicalInfoVendorID		DisplayString,
		raidPhysicalInfoProductID		DisplayString,
		raidPhysicalInfoSerialNumber	DisplayString,
		raidPhysicalInfoPowerState		DisplayString,
		raidPhysicalInfoInterfaceType	DisplayString
--		raidPhysicalInfoFWRevision		DisplayString
	}		
	raidPhysicalInfoIndex  OBJECT-TYPE
		SYNTAX 			Integer32
		MAX-ACCESS		read-only
		STATUS			current
		DESCRIPTION 
		"
			The index value which uniquely identifies the interface to which this entry is applicable.
		"
		::= {raidPhysicalInfoEntry 1}
	raidPhysicalInfoDeviceID  OBJECT-TYPE
		SYNTAX 			Integer32
		MAX-ACCESS		read-only
		STATUS			current
		DESCRIPTION 
		"
			The device id associated with the Raid of this entry .
		"
		::= {raidPhysicalInfoEntry 2} 
	raidPhysicalInfoController  OBJECT-TYPE
		SYNTAX 			DisplayString
		MAX-ACCESS		read-only
		STATUS			current
		DESCRIPTION 
		"
			The controller associated with the Raid of this entry .
		"
		::= {raidPhysicalInfoEntry 3}		
	raidPhysicalInfoMediaType  OBJECT-TYPE
		SYNTAX 			DisplayString
		MAX-ACCESS		read-only
		STATUS			current
		DESCRIPTION 
		"
			The media type associated with the Raid of this entry .
		"
		::= {raidPhysicalInfoEntry 4}
	raidPhysicalInfoState  OBJECT-TYPE
		SYNTAX 			DisplayString
		MAX-ACCESS		read-only
		STATUS			current
		DESCRIPTION 
		"
			The state associated with the Raid of this entry .
		"
		::= {raidPhysicalInfoEntry 5}
	raidPhysicalInfoSlot  OBJECT-TYPE
		SYNTAX 			Integer32
		MAX-ACCESS		read-only
		STATUS			current
		DESCRIPTION 
		"
			The slot version associated with the Raid of this entry .
		"
		::= {raidPhysicalInfoEntry 6}
	raidPhysicalInfoSpeed  OBJECT-TYPE
		SYNTAX 			DisplayString
		MAX-ACCESS		read-only
		STATUS			current
		DESCRIPTION 
		"
			The speed associated with the Raid of this entry .
		"
		::= {raidPhysicalInfoEntry 7}
	raidPhysicalInfoLinkSpeed  OBJECT-TYPE
		SYNTAX 			DisplayString
		MAX-ACCESS		read-only
		STATUS			current
		DESCRIPTION 
		"
			The link speed name associated with the Raid of this entry .
		"
		::= {raidPhysicalInfoEntry 8}
	raidPhysicalInfoSize  OBJECT-TYPE
		SYNTAX 			DisplayString
		MAX-ACCESS		read-only
		STATUS			current
		DESCRIPTION 
		"
			The size associated with the Raid of this entry .
		"
		::= {raidPhysicalInfoEntry 9}
	raidPhysicalInfoTemp  OBJECT-TYPE
		SYNTAX 			DisplayString
		MAX-ACCESS		read-only
		STATUS			current
		DESCRIPTION 
		"
			The temperature associated with the Raid of this entry .
		"
		::= {raidPhysicalInfoEntry 10}
--	raidPhysicalInfoLocateStatus  OBJECT-TYPE
--		SYNTAX 			DisplayString
--		MAX-ACCESS		read-only
--		STATUS			current
--		DESCRIPTION 
--		"
--			The locate status id name associated with the Raid of this entry .
--		"
--		::= {raidPhysicalInfoEntry 11}
	raidPhysicalInfoVendorID  OBJECT-TYPE
		SYNTAX 			DisplayString
		MAX-ACCESS		read-only
		STATUS			current
		DESCRIPTION 
		"
			The vendor id associated with the Raid of this entry .
		"
		::= {raidPhysicalInfoEntry 11}
	raidPhysicalInfoProductID  OBJECT-TYPE
		SYNTAX 			DisplayString
		MAX-ACCESS		read-only
		STATUS			current
		DESCRIPTION 
		"
			The product id system id associated with the Raid of this entry .
		"
		::= {raidPhysicalInfoEntry 12}
	raidPhysicalInfoSerialNumber  OBJECT-TYPE
		SYNTAX 			DisplayString
		MAX-ACCESS		read-only
		STATUS			current
		DESCRIPTION 
		"
			The serial number associated with the Raid of this entry .
		"
		::= {raidPhysicalInfoEntry 13}
	raidPhysicalInfoPowerState  OBJECT-TYPE
		SYNTAX 			DisplayString
		MAX-ACCESS		read-only
		STATUS			current
		DESCRIPTION 
		"
			The power state associated with the Raid of this entry .
		"
		::= {raidPhysicalInfoEntry 14}
	raidPhysicalInfoInterfaceType  OBJECT-TYPE
		SYNTAX 			DisplayString
		MAX-ACCESS		read-only
		STATUS			current
		DESCRIPTION 
		"
			The interface type associated with the Raid of this entry .
		"
		::= {raidPhysicalInfoEntry 15}
--	raidPhysicalInfoFWRevision  OBJECT-TYPE
--		SYNTAX 			DisplayString
--		MAX-ACCESS		read-only
--		STATUS			current
--		DESCRIPTION 
--		"
--			The FW Revision associated with the Raid of this entry .
--		"
--		::= {raidPhysicalInfoEntry 17}
--raidPhysicalInfoTable end
--raidLogicalInfoTable start
	raidLogicalInfoTable	OBJECT-TYPE
	    SYNTAX     SEQUENCE OF RaidLogicalInfoEntry
	    MAX-ACCESS read-only
	    STATUS     current
	    DESCRIPTION
	           "The table of Logical information relevant to this entity's Raid"
	 	::= {serverAssetInfo 22}  
	 
	raidLogicalInfoEntry OBJECT-TYPE
	    SYNTAX     RaidLogicalInfoEntry
	    MAX-ACCESS read-only
	    STATUS     current
	    DESCRIPTION
	           "The Logical information for one of this entity's Raid."
	    INDEX   { 
				  raidLogicalInfoIndex
	            }
	    ::= { raidLogicalInfoTable 1 }   
	
	RaidLogicalInfoEntry ::= 
	SEQUENCE {
	    raidLogicalInfoIndex     		Integer32,
		raidLogicalInfoLDName			DisplayString,
		raidLogicalInfoController		DisplayString,
		raidLogicalInfoType				DisplayString,
		raidLogicalInfoState			DisplayString,
		raidLogicalInfoReadPolicy		DisplayString,
		raidLogicalInfoWritePolicy		DisplayString,
		raidLogicalInfoIoPolicy			DisplayString,
		raidLogicalInfoAccessPolicy		DisplayString,
		raidLogicalInfoNoOfPhyDevices	Integer32,
		raidLogicalInfoStripeSize		DisplayString,
		raidLogicalInfoBGI				DisplayString,
		raidLogicalInfoProgress			DisplayString,
		raidLogicalInfoBadBlocksTable	DisplayString,
		raidLogicalInfoSize				DisplayString
	}		
	raidLogicalInfoIndex  OBJECT-TYPE
		SYNTAX 			Integer32
		MAX-ACCESS		read-only
		STATUS			current
		DESCRIPTION 
		"
			The index value which uniquely identifies the interface to which this entry is applicable.
		"
		::= {raidLogicalInfoEntry 1}
	raidLogicalInfoLDName  OBJECT-TYPE
		SYNTAX 			DisplayString
		MAX-ACCESS		read-only
		STATUS			current
		DESCRIPTION 
		"
			The ld name associated with the Raid of this entry .
		"
		::= {raidLogicalInfoEntry 2} 
	raidLogicalInfoController  OBJECT-TYPE
		SYNTAX 			DisplayString
		MAX-ACCESS		read-only
		STATUS			current
		DESCRIPTION 
		"
			The controller name associated with the Raid of this entry .
		"
		::= {raidLogicalInfoEntry 3}		
	raidLogicalInfoType  OBJECT-TYPE
		SYNTAX 			DisplayString
		MAX-ACCESS		read-only
		STATUS			current
		DESCRIPTION 
		"
			The type associated with the Raid of this entry .
		"
		::= {raidLogicalInfoEntry 4}
	raidLogicalInfoState  OBJECT-TYPE
		SYNTAX 			DisplayString
		MAX-ACCESS		read-only
		STATUS			current
		DESCRIPTION 
		"
			The state associated with the Raid of this entry .
		"
		::= {raidLogicalInfoEntry 5}
	raidLogicalInfoReadPolicy  OBJECT-TYPE
		SYNTAX 			DisplayString
		MAX-ACCESS		read-only
		STATUS			current
		DESCRIPTION 
		"
			The read policy associated with the Raid of this entry .
		"
		::= {raidLogicalInfoEntry 6}
	raidLogicalInfoWritePolicy  OBJECT-TYPE
		SYNTAX 			DisplayString
		MAX-ACCESS		read-only
		STATUS			current
		DESCRIPTION 
		"
			The write policy associated with the Raid of this entry .
		"
		::= {raidLogicalInfoEntry 7}
	raidLogicalInfoIoPolicy  OBJECT-TYPE
		SYNTAX 			DisplayString
		MAX-ACCESS		read-only
		STATUS			current
		DESCRIPTION 
		"
			The cache policy associated with the Raid of this entry .
		"
		::= {raidLogicalInfoEntry 8}
	raidLogicalInfoAccessPolicy  OBJECT-TYPE
		SYNTAX 			DisplayString
		MAX-ACCESS		read-only
		STATUS			current
		DESCRIPTION 
		"
			The access policy associated with the Raid of this entry .
		"
		::= {raidLogicalInfoEntry 9}
	raidLogicalInfoNoOfPhyDevices  OBJECT-TYPE
		SYNTAX 			Integer32
		MAX-ACCESS		read-only
		STATUS			current
		DESCRIPTION 
		"
			The number of phy devices associated with the Raid of this entry .
		"
		::= {raidLogicalInfoEntry 10}
	raidLogicalInfoStripeSize  OBJECT-TYPE
		SYNTAX 			DisplayString
		MAX-ACCESS		read-only
		STATUS			current
		DESCRIPTION 
		"
			The stripe size associated with the Raid of this entry .
		"
		::= {raidLogicalInfoEntry 11}
	raidLogicalInfoBGI  OBJECT-TYPE
		SYNTAX 			DisplayString
		MAX-ACCESS		read-only
		STATUS			current
		DESCRIPTION 
		"
			The bgi system id associated with the Raid of this entry .
		"
		::= {raidLogicalInfoEntry 12}
	raidLogicalInfoProgress  OBJECT-TYPE
		SYNTAX 			DisplayString
		MAX-ACCESS		read-only
		STATUS			current
		DESCRIPTION 
		"
			The progress associated with the Raid of this entry .
		"
		::= {raidLogicalInfoEntry 13}
	raidLogicalInfoBadBlocksTable  OBJECT-TYPE
		SYNTAX 			DisplayString
		MAX-ACCESS		read-only
		STATUS			current
		DESCRIPTION 
		"
			The bad blocks table associated with the Raid of this entry .
		"
		::= {raidLogicalInfoEntry 14}
	raidLogicalInfoSize  OBJECT-TYPE
		SYNTAX 			DisplayString
		MAX-ACCESS		read-only
		STATUS			current
		DESCRIPTION 
		"
			The size associated with the Raid of this entry .
		"
		::= {raidLogicalInfoEntry 15}
--raidLogicalInfoTable end		
--BBUInfoTable start
	raidBBUInfoTable	OBJECT-TYPE
	    SYNTAX     SEQUENCE OF RaidBBUInfoEntry
	    MAX-ACCESS read-only
	    STATUS     current
	    DESCRIPTION
	           "The table of Logical information relevant to this entity's Raid"
	 	::= {serverAssetInfo 23}  
	 
	raidBBUInfoEntry OBJECT-TYPE
	    SYNTAX     RaidBBUInfoEntry
	    MAX-ACCESS read-only
	    STATUS     current
	    DESCRIPTION
	           "The Logical information for one of this entity's Raid."
	    INDEX   { 
				  raidBBUInfoIndex
	            }
	    ::= { raidBBUInfoTable 1 }   
	
	RaidBBUInfoEntry ::= 
	SEQUENCE {
	    raidBBUInfoIndex     		Integer32,
		raidBBUInfoController		DisplayString,
--		raidBBUInfoDeviceName		DisplayString,
		raidBBUInfoControllerId    	DisplayString,
		raidBBUInfoType				DisplayString,
		raidBBUInfoStatus			DisplayString,
		raidBBUInfoTemp				DisplayString,
		raidBBUInfoVoltage			DisplayString,
		raidBBUInfoCurrent			DisplayString
	}		
	raidBBUInfoIndex  OBJECT-TYPE
		SYNTAX 			Integer32
		MAX-ACCESS		read-only
		STATUS			current
		DESCRIPTION 
		"
			The index value which uniquely identifies the interface to which this entry is applicable.
		"
		::= {raidBBUInfoEntry 1}
	raidBBUInfoController  OBJECT-TYPE
		SYNTAX 			DisplayString
		MAX-ACCESS		read-only
		STATUS			current
		DESCRIPTION 
		"
			The controller name associated with the Raid of this entry .
		"
		::= {raidBBUInfoEntry 2} 
	raidBBUInfoControllerId  OBJECT-TYPE
		SYNTAX 			DisplayString
		MAX-ACCESS		read-only
		STATUS			current
		DESCRIPTION 
		"
			The ControllerId associated with the Raid of this entry .
		"
		::= {raidBBUInfoEntry 3}
	raidBBUInfoType  OBJECT-TYPE
		SYNTAX 			DisplayString
		MAX-ACCESS		read-only
		STATUS			current
		DESCRIPTION 
		"
			The type associated with the Raid of this entry .
		"
		::= {raidBBUInfoEntry 4}	
	raidBBUInfoStatus  OBJECT-TYPE
		SYNTAX 			DisplayString
		MAX-ACCESS		read-only
		STATUS			current
		DESCRIPTION 
		"
			The status associated with the Raid of this entry .
		"
		::= {raidBBUInfoEntry 5} 
	raidBBUInfoTemp  OBJECT-TYPE
		SYNTAX 			DisplayString
		MAX-ACCESS		read-only
		STATUS			current
		DESCRIPTION 
		"
			The temperature associated with the Raid of this entry .
		"
		::= {raidBBUInfoEntry 6}	
	raidBBUInfoVoltage  OBJECT-TYPE
		SYNTAX 			DisplayString
		MAX-ACCESS		read-only
		STATUS			current
		DESCRIPTION 
		"
			The voltage associated with the Raid of this entry .
		"
		::= {raidBBUInfoEntry 7} 
	raidBBUInfoCurrent  OBJECT-TYPE
		SYNTAX 			DisplayString
		MAX-ACCESS		read-only
		STATUS			current
		DESCRIPTION 
		"
			The current associated with the Raid of this entry .
		"
		::= {raidBBUInfoEntry 8}		
--raidBBUInfoTable end
--raidStorgeSummaryTable start
	raidStorgeSummaryTable	OBJECT-TYPE
	    SYNTAX     SEQUENCE OF RaidStorgeSummaryEntry
	    MAX-ACCESS read-only
	    STATUS     current
	    DESCRIPTION
	           "The table of raid storge summary information relevant to this entity's Raid"
	 	::= {serverAssetInfo 24}  
	 
	raidStorgeSummaryEntry OBJECT-TYPE
	    SYNTAX     RaidStorgeSummaryEntry
	    MAX-ACCESS read-only
	    STATUS     current
	    DESCRIPTION
	           "The raid storge summary information for one of this entity's Raid."
	    INDEX   { 
				  raidStorgeSummaryIndex
	            }
	    ::= { raidStorgeSummaryTable 1 }   
	
	RaidStorgeSummaryEntry ::= 
	SEQUENCE {
	    raidStorgeSummaryIndex     		Integer32,
		raidStorgeSummaryController		DisplayString,
		physicalDevicesCount			Integer32,
		logicalDevicesCount				Integer32,
		hotSparesCount					Integer32,
		ldDegradedCount			        Integer32,
		ldOfflineCount				    Integer32,
		pdDiskPresentCount				Integer32,
		pdDiskPredFailedCount			Integer32,
		pdDiskFailedCount				Integer32,
		arrayConfigCount				Integer32,
		memCorrectErrorCount			Integer32,
		unMemCorrectErrorCount			Integer32,
		eccBucketCount					Integer32,
		pdUnlockedForeignCount			Integer32,
		pdLockedForeignCount			Integer32
	}		
	raidStorgeSummaryIndex  OBJECT-TYPE
		SYNTAX 			Integer32
		MAX-ACCESS		read-only
		STATUS			current
		DESCRIPTION 
		"
			The index value which uniquely identifies the interface to which this entry is applicable.
		"
		::= {raidStorgeSummaryEntry 1}
	raidStorgeSummaryController  OBJECT-TYPE
		SYNTAX 			DisplayString
		MAX-ACCESS		read-only
		STATUS			current
		DESCRIPTION 
		"
			The controller name associated with the Raid of this entry .
		"
		::= {raidStorgeSummaryEntry 2} 
	physicalDevicesCount  OBJECT-TYPE
		SYNTAX 			Integer32
		MAX-ACCESS		read-only
		STATUS			current
		DESCRIPTION 
		"
			The physical device count associated with the Raid of this entry .
		"
		::= {raidStorgeSummaryEntry 3}	
	logicalDevicesCount  OBJECT-TYPE
		SYNTAX 			Integer32
		MAX-ACCESS		read-only
		STATUS			current
		DESCRIPTION 
		"
			The logical device count associated with the Raid of this entry .
		"
		::= {raidStorgeSummaryEntry 4} 
	hotSparesCount  OBJECT-TYPE
		SYNTAX 			Integer32
		MAX-ACCESS		read-only
		STATUS			current
		DESCRIPTION 
		"
			The hot spare count associated with the Raid of this entry .
		"
		::= {raidStorgeSummaryEntry 5}		
	ldDegradedCount  OBJECT-TYPE
		SYNTAX 			Integer32
		MAX-ACCESS		read-only
		STATUS			current
		DESCRIPTION 
		"
			Degraded physical device count with the Raid of this entry .
		"
		::= {raidStorgeSummaryEntry 6}	
	ldOfflineCount  OBJECT-TYPE
		SYNTAX 			Integer32
		MAX-ACCESS		read-only
		STATUS			current
		DESCRIPTION 
		"
			Offline logical device count with the Raid of this entry .
		"
		::= {raidStorgeSummaryEntry 7} 
	pdDiskPresentCount  OBJECT-TYPE
		SYNTAX 			Integer32
		MAX-ACCESS		read-only
		STATUS			current
		DESCRIPTION 
		"
			Present physical device count with the Raid of this entry .
		"
		::= {raidStorgeSummaryEntry 8}	
	pdDiskPredFailedCount  OBJECT-TYPE
		SYNTAX 			Integer32
		MAX-ACCESS		read-only
		STATUS			current
		DESCRIPTION 
		"
			Pre failed physical device count with the Raid of this entry .
		"
		::= {raidStorgeSummaryEntry 9}	
	pdDiskFailedCount  OBJECT-TYPE
		SYNTAX 			Integer32
		MAX-ACCESS		read-only
		STATUS			current
		DESCRIPTION 
		"
			Failed physical device count with the Raid of this entry .
		"
		::= {raidStorgeSummaryEntry 10} 
	arrayConfigCount  OBJECT-TYPE
		SYNTAX 			Integer32
		MAX-ACCESS		read-only
		STATUS			current
		DESCRIPTION 
		"
			Array config count with the Raid of this entry .
		"
		::= {raidStorgeSummaryEntry 11}	
	memCorrectErrorCount  OBJECT-TYPE
		SYNTAX 			Integer32
		MAX-ACCESS		read-only
		STATUS			current
		DESCRIPTION 
		"
			Error mem count with the Raid of this entry .
		"
		::= {raidStorgeSummaryEntry 12}	
	unMemCorrectErrorCount  OBJECT-TYPE
		SYNTAX 			Integer32
		MAX-ACCESS		read-only
		STATUS			current
		DESCRIPTION 
		"
			Un correct mem count with the Raid of this entry .
		"
		::= {raidStorgeSummaryEntry 13} 
	eccBucketCount  OBJECT-TYPE
		SYNTAX 			Integer32
		MAX-ACCESS		read-only
		STATUS			current
		DESCRIPTION 
		"
			Ecc bucket count with the Raid of this entry .
		"
		::= {raidStorgeSummaryEntry 14}	
	pdUnlockedForeignCount  OBJECT-TYPE
		SYNTAX 			Integer32
		MAX-ACCESS		read-only
		STATUS			current
		DESCRIPTION 
		"
			Unlocked foreign physical device count with the Raid of this entry .
		"
		::= {raidStorgeSummaryEntry 15}	
	pdLockedForeignCount  OBJECT-TYPE
		SYNTAX 			Integer32
		MAX-ACCESS		read-only
		STATUS			current
		DESCRIPTION 
		"
			Locked foreign physical device count with the Raid of this entry .
		"
		::= {raidStorgeSummaryEntry 16} 
--raidStorgeSummary end
--sasitControllerInfoTable start
	sasitControllerInfoTable	OBJECT-TYPE
	    SYNTAX     SEQUENCE OF SasitControllerInfoEntry
	    MAX-ACCESS read-only
	    STATUS     current
	    DESCRIPTION
	           "The table of SAS IT storge summary information relevant to this entity's SAS IT."
	 	::= {serverAssetInfo 25}  
	 
	sasitControllerInfoEntry OBJECT-TYPE
	    SYNTAX     SasitControllerInfoEntry
	    MAX-ACCESS read-only
	    STATUS     current
	    DESCRIPTION
	           "The SAS IT storge summary information for one of this entity's SAS IT."
	    INDEX   { 
				  sasitControllerIndex
	            }
	    ::= { sasitControllerInfoTable 1 }   
	
	SasitControllerInfoEntry ::= 
	SEQUENCE {
	    sasitControllerIndex    		Integer32,
		sasitControllerName				DisplayString,
		sasitControllerBoardName		DisplayString,
--		sasitControllerSASAddress		DisplayString,
		sasitControllerFwVersion		DisplayString,
		sasitControllerNVDATAVersion	DisplayString,
		sasitControllerPCIVendorID		DisplayString,
		sasitControllerPCIDeviceID		DisplayString,
		sasitControllerPCISubVendorID	DisplayString,
		sasitControllerPCISubSystemID	DisplayString,
		sasitControllerSpeed			DisplayString,
		sasitControllerIOCTemp			DisplayString
	}		
	sasitControllerIndex  OBJECT-TYPE
		SYNTAX 			Integer32
		MAX-ACCESS		read-only
		STATUS			current
		DESCRIPTION 
		"
			The index value which uniquely identifies the interface to which this entry is applicable.
		"
		::= {sasitControllerInfoEntry 1}
	sasitControllerName  OBJECT-TYPE
		SYNTAX 			DisplayString
		MAX-ACCESS		read-only
		STATUS			current
		DESCRIPTION 
		"
			The controller name associated with the SAS IT of this entry .
		"
		::= {sasitControllerInfoEntry 2} 
	sasitControllerBoardName  OBJECT-TYPE
		SYNTAX 			DisplayString
		MAX-ACCESS		read-only
		STATUS			current
		DESCRIPTION 
		"
			The board name associated with the SAS IT of this entry .
		"
		::= {sasitControllerInfoEntry 3}	
--	sasitControllerSASAddress  OBJECT-TYPE
--		SYNTAX 			DisplayString
--		MAX-ACCESS		read-only
--		STATUS			current
--		DESCRIPTION 
--		"
--			The sas address associated with the SAS IT of this entry .
--		"
--		::= {sasitControllerInfoEntry 4} 
	sasitControllerFwVersion  OBJECT-TYPE
		SYNTAX 			DisplayString
		MAX-ACCESS		read-only
		STATUS			current
		DESCRIPTION 
		"
			The firmware version associated with the SAS IT of this entry .
		"
		::= {sasitControllerInfoEntry 4}		
	sasitControllerNVDATAVersion  OBJECT-TYPE
		SYNTAX 			DisplayString
		MAX-ACCESS		read-only
		STATUS			current
		DESCRIPTION 
		"
			The NVDATA version associated with the SAS IT of this entry .
		"
		::= {sasitControllerInfoEntry 5} 
	sasitControllerPCIVendorID  OBJECT-TYPE
		SYNTAX 			DisplayString
		MAX-ACCESS		read-only
		STATUS			current
		DESCRIPTION 
		"
			The pci vendor id associated with the SAS IT of this entry .
		"
		::= {sasitControllerInfoEntry 6}	
	sasitControllerPCIDeviceID  OBJECT-TYPE
		SYNTAX 			DisplayString
		MAX-ACCESS		read-only
		STATUS			current
		DESCRIPTION 
		"
			The pci device id associated with the SAS IT of this entry .
		"
		::= {sasitControllerInfoEntry 7} 
	sasitControllerPCISubVendorID  OBJECT-TYPE
		SYNTAX 			DisplayString
		MAX-ACCESS		read-only
		STATUS			current
		DESCRIPTION 
		"
			The pci sub vendor id associated with the SAS IT of this entry .
		"
		::= {sasitControllerInfoEntry 8}
	sasitControllerPCISubSystemID  OBJECT-TYPE
		SYNTAX 			DisplayString
		MAX-ACCESS		read-only
		STATUS			current
		DESCRIPTION 
		"
			The pci sub system id associated with the SAS IT of this entry .
		"
		::= {sasitControllerInfoEntry 9} 
	sasitControllerSpeed  OBJECT-TYPE
		SYNTAX 			DisplayString
		MAX-ACCESS		read-only
		STATUS			current
		DESCRIPTION 
		"
			The controller speed associated with the SAS IT of this entry .
		"
		::= {sasitControllerInfoEntry 10}	
	sasitControllerIOCTemp  OBJECT-TYPE
		SYNTAX 			DisplayString
		MAX-ACCESS		read-only
		STATUS			current
		DESCRIPTION 
		"
			The ioc temperature associated with the SAS IT of this entry .
		"
		::= {sasitControllerInfoEntry 11} 
--sasitControllerInfoTable end
--sasitPhysicalInfoTable start
	sasitPhysicalInfoTable	OBJECT-TYPE
	    SYNTAX     SEQUENCE OF SasitPhysicalInfoEntry
	    MAX-ACCESS read-only
	    STATUS     current
	    DESCRIPTION
	           "The table of physical information relevant to this entity's SAS IT."
	 	::= {serverAssetInfo 26}  
	 
	sasitPhysicalInfoEntry OBJECT-TYPE
	    SYNTAX     SasitPhysicalInfoEntry
	    MAX-ACCESS read-only
	    STATUS     current
	    DESCRIPTION
	           "The physical information for one of this entity's SAS IT."
	    INDEX   { 
				  sasitPhysicalInfoIndex
	            }
	    ::= { sasitPhysicalInfoTable 1 }   
	
	SasitPhysicalInfoEntry ::= 
	SEQUENCE {
	    sasitPhysicalInfoIndex     		Integer32,
		sasitPhysicalInfoDeviceID		Integer32,
		sasitPhysicalInfoController		DisplayString,
		sasitPhysicalInfoMediaType		DisplayString,
		sasitPhysicalInfoState			DisplayString,
		sasitPhysicalInfoSlot			Integer32,
		sasitPhysicalInfoSpeed			DisplayString,
		sasitPhysicalInfoSize			DisplayString,
		sasitPhysicalInfoTemp			DisplayString,
		sasitPhysicalInfoVendorID		DisplayString,
		sasitPhysicalInfoProductID		DisplayString,
		sasitPhysicalInfoSerialNumber	DisplayString,
		sasitPhysicalInfoFwVersion		DisplayString,
		sasitPhysicalInfoPowerState		DisplayString,
		sasitPhysicalInfoInterfaceType	DisplayString,
		sasitPhysicalInfoSmart			DisplayString
	}		
	sasitPhysicalInfoIndex  OBJECT-TYPE
		SYNTAX 			Integer32
		MAX-ACCESS		read-only
		STATUS			current
		DESCRIPTION 
		"
			The index value which uniquely identifies the interface to which this entry is applicable.
		"
		::= {sasitPhysicalInfoEntry 1}
	sasitPhysicalInfoDeviceID  OBJECT-TYPE
		SYNTAX 			Integer32
		MAX-ACCESS		read-only
		STATUS			current
		DESCRIPTION 
		"
			The device id associated with the SAS IT of this entry .
		"
		::= {sasitPhysicalInfoEntry 2} 
	sasitPhysicalInfoController  OBJECT-TYPE
		SYNTAX 			DisplayString
		MAX-ACCESS		read-only
		STATUS			current
		DESCRIPTION 
		"
			The name associated with the SAS IT of this entry .
		"
		::= {sasitPhysicalInfoEntry 3}		
	sasitPhysicalInfoMediaType  OBJECT-TYPE
		SYNTAX 			DisplayString
		MAX-ACCESS		read-only
		STATUS			current
		DESCRIPTION 
		"
			The media type associated with the SAS IT of this entry .
		"
		::= {sasitPhysicalInfoEntry 4}
	sasitPhysicalInfoState  OBJECT-TYPE
		SYNTAX 			DisplayString
		MAX-ACCESS		read-only
		STATUS			current
		DESCRIPTION 
		"
			The state associated with the SAS IT of this entry .
		"
		::= {sasitPhysicalInfoEntry 5}
	sasitPhysicalInfoSlot  OBJECT-TYPE
		SYNTAX 			Integer32
		MAX-ACCESS		read-only
		STATUS			current
		DESCRIPTION 
		"
			The slot version associated with the SAS IT of this entry .
		"
		::= {sasitPhysicalInfoEntry 6}
	sasitPhysicalInfoSpeed  OBJECT-TYPE
		SYNTAX 			DisplayString
		MAX-ACCESS		read-only
		STATUS			current
		DESCRIPTION 
		"
			The speed associated with the SAS IT of this entry .
		"
		::= {sasitPhysicalInfoEntry 7}
	sasitPhysicalInfoSize  OBJECT-TYPE
		SYNTAX 			DisplayString
		MAX-ACCESS		read-only
		STATUS			current
		DESCRIPTION 
		"
			The size associated with the SAS IT of this entry .
		"
		::= {sasitPhysicalInfoEntry 8}
	sasitPhysicalInfoTemp  OBJECT-TYPE
		SYNTAX 			DisplayString
		MAX-ACCESS		read-only
		STATUS			current
		DESCRIPTION 
		"
			The temperature associated with the SAS IT of this entry .
		"
		::= {sasitPhysicalInfoEntry 9}
	sasitPhysicalInfoVendorID  OBJECT-TYPE
		SYNTAX 			DisplayString
		MAX-ACCESS		read-only
		STATUS			current
		DESCRIPTION 
		"
			The vendor id associated with the SAS IT of this entry .
		"
		::= {sasitPhysicalInfoEntry 10}
	sasitPhysicalInfoProductID  OBJECT-TYPE
		SYNTAX 			DisplayString
		MAX-ACCESS		read-only
		STATUS			current
		DESCRIPTION 
		"
			The product id associated with the SAS IT of this entry .
		"
		::= {sasitPhysicalInfoEntry 11}
	sasitPhysicalInfoSerialNumber  OBJECT-TYPE
		SYNTAX 			DisplayString
		MAX-ACCESS		read-only
		STATUS			current
		DESCRIPTION 
		"
			The serial number associated with the SAS IT of this entry .
		"
		::= {sasitPhysicalInfoEntry 12}
	sasitPhysicalInfoFwVersion  OBJECT-TYPE
		SYNTAX 			DisplayString
		MAX-ACCESS		read-only
		STATUS			current
		DESCRIPTION 
		"
			The firmware version associated with the SAS IT of this entry .
		"
		::= {sasitPhysicalInfoEntry 13}
	sasitPhysicalInfoPowerState  OBJECT-TYPE
		SYNTAX 			DisplayString
		MAX-ACCESS		read-only
		STATUS			current
		DESCRIPTION 
		"
			The power state associated with the SAS IT of this entry .
		"
		::= {sasitPhysicalInfoEntry 14}
	sasitPhysicalInfoInterfaceType  OBJECT-TYPE
		SYNTAX 			DisplayString
		MAX-ACCESS		read-only
		STATUS			current
		DESCRIPTION 
		"
			The interface type associated with the SAS IT of this entry .
		"
		::= {sasitPhysicalInfoEntry 15}
	sasitPhysicalInfoSmart  OBJECT-TYPE
		SYNTAX 			DisplayString
		MAX-ACCESS		read-only
		STATUS			current
		DESCRIPTION 
		"
			The smart associated with the SAS IT of this entry .
		"
		::= {sasitPhysicalInfoEntry 16}
--sasitPhysicalInfoTable end
--sensorlistInfoTable start
	sensorlistInfoTable	OBJECT-TYPE
	    SYNTAX     SEQUENCE OF SensorlistInfoEntry
	    MAX-ACCESS read-only
	    STATUS     current
	    DESCRIPTION
	           "The table display Sensor name"
	 	::= {serverAssetInfo 27}
		
	sensorlistInfoEntry OBJECT-TYPE
	    SYNTAX     SensorlistInfoEntry
	    MAX-ACCESS read-only
	    STATUS     current
	    DESCRIPTION
	           "The table display Sensor name."
	    INDEX   { 
				  sensorlistInfoIndex
	            }
	    ::= { sensorlistInfoTable 1 }
		
	SensorlistInfoEntry ::= 
	SEQUENCE {
	    sensorlistInfoIndex     Integer32,
		sensorName1       DisplayString,
		sensorName2       DisplayString,
		sensorName3       DisplayString,
		sensorName4       DisplayString,
		sensorName5       DisplayString,
		sensorName6       DisplayString,
		sensorName7       DisplayString,
		sensorName8       DisplayString,
		sensorName9       DisplayString,
		sensorName10       DisplayString,
		sensorName11       DisplayString,
		sensorName12       DisplayString,
		sensorName13       DisplayString,
		sensorName14       DisplayString,
		sensorName15       DisplayString,
		sensorName16       DisplayString,
		sensorName17       DisplayString,
		sensorName18       DisplayString,
		sensorName19       DisplayString,
		sensorName20       DisplayString,
		sensorName21       DisplayString,
		sensorName22       DisplayString,
		sensorName23       DisplayString,
		sensorName24       DisplayString,
		sensorName25       DisplayString,
		sensorName26       DisplayString,
		sensorName27       DisplayString,
		sensorName28       DisplayString,
		sensorName29       DisplayString,
		sensorName30       DisplayString,
		sensorName31       DisplayString,
		sensorName32       DisplayString,
		sensorName33       DisplayString,
		sensorName34       DisplayString,
		sensorName35       DisplayString,
		sensorName36       DisplayString,
		sensorName37       DisplayString,
		sensorName38       DisplayString,
		sensorName39       DisplayString,
		sensorName40       DisplayString,
		sensorName41       DisplayString,
		sensorName42       DisplayString,
		sensorName43       DisplayString,
		sensorName44       DisplayString,
		sensorName45       DisplayString,
		sensorName46       DisplayString,
		sensorName47       DisplayString,
		sensorName48       DisplayString,
		sensorName49       DisplayString,
		sensorName50       DisplayString,
		sensorName51       DisplayString,
		sensorName52       DisplayString,
		sensorName53       DisplayString,
		sensorName54       DisplayString,
		sensorName55       DisplayString,
		sensorName56       DisplayString,
		sensorName57       DisplayString,
		sensorName58       DisplayString,
		sensorName59       DisplayString,
		sensorName60       DisplayString,
		sensorName61       DisplayString,
		sensorName62       DisplayString,
		sensorName63       DisplayString,
		sensorName64       DisplayString,
		sensorName65       DisplayString,
		sensorName66       DisplayString,
		sensorName67       DisplayString,
		sensorName68       DisplayString,
		sensorName69       DisplayString,
		sensorName70       DisplayString,
		sensorName71       DisplayString,
		sensorName72       DisplayString,
		sensorName73       DisplayString,
		sensorName74       DisplayString,
		sensorName75       DisplayString,
		sensorName76       DisplayString,
		sensorName77       DisplayString,
		sensorName78       DisplayString,
		sensorName79       DisplayString,
		sensorName80       DisplayString,
		sensorName81       DisplayString,
		sensorName82       DisplayString,
		sensorName83       DisplayString,
		sensorName84       DisplayString,
		sensorName85       DisplayString,
		sensorName86       DisplayString,
		sensorName87       DisplayString,
		sensorName88       DisplayString,
		sensorName89       DisplayString,
		sensorName90       DisplayString,
		sensorName91       DisplayString,
		sensorName92       DisplayString,
		sensorName93       DisplayString,
		sensorName94       DisplayString,
		sensorName95       DisplayString,
		sensorName96       DisplayString,
		sensorName97       DisplayString,
		sensorName98       DisplayString,
		sensorName99       DisplayString,
		sensorName100       DisplayString,
		sensorName101       DisplayString,
		sensorName102       DisplayString,
		sensorName103       DisplayString,
		sensorName104       DisplayString,
		sensorName105       DisplayString,
		sensorName106       DisplayString,
		sensorName107       DisplayString,
		sensorName108       DisplayString,
		sensorName109       DisplayString,
		sensorName110       DisplayString,
		sensorName111       DisplayString,
		sensorName112       DisplayString,
		sensorName113       DisplayString,
		sensorName114       DisplayString,
		sensorName115       DisplayString,
		sensorName116       DisplayString,
		sensorName117       DisplayString,
		sensorName118       DisplayString,
		sensorName119       DisplayString,
		sensorName120       DisplayString,
		sensorName121       DisplayString,
		sensorName122       DisplayString,
		sensorName123       DisplayString,
		sensorName124       DisplayString,
		sensorName125       DisplayString,
		sensorName126       DisplayString,
		sensorName127       DisplayString,
		sensorName128       DisplayString,
		sensorName129       DisplayString,
		sensorName130       DisplayString,
		sensorName131       DisplayString,
		sensorName132       DisplayString,
		sensorName133       DisplayString,
		sensorName134       DisplayString,
		sensorName135       DisplayString,
		sensorName136       DisplayString,
		sensorName137       DisplayString,
		sensorName138       DisplayString,
		sensorName139       DisplayString,
		sensorName140       DisplayString,
		sensorName141       DisplayString,
		sensorName142       DisplayString,
		sensorName143       DisplayString,
		sensorName144       DisplayString,
		sensorName145       DisplayString,
		sensorName146       DisplayString,
		sensorName147       DisplayString,
		sensorName148       DisplayString,
		sensorName149       DisplayString,
		sensorName150       DisplayString,
		sensorName151       DisplayString,
		sensorName152       DisplayString,
		sensorName153       DisplayString,
		sensorName154       DisplayString,
		sensorName155       DisplayString,
		sensorName156       DisplayString,
		sensorName157       DisplayString,
		sensorName158       DisplayString,
		sensorName159       DisplayString,
		sensorName160       DisplayString,
		sensorName161       DisplayString,
		sensorName162       DisplayString,
		sensorName163       DisplayString,
		sensorName164       DisplayString,
		sensorName165       DisplayString,
		sensorName166       DisplayString,
		sensorName167       DisplayString,
		sensorName168       DisplayString,
		sensorName169       DisplayString,
		sensorName170       DisplayString,
		sensorName171       DisplayString,
		sensorName172       DisplayString,
		sensorName173       DisplayString,
		sensorName174       DisplayString,
		sensorName175       DisplayString,
		sensorName176       DisplayString,
		sensorName177       DisplayString,
		sensorName178       DisplayString,
		sensorName179       DisplayString,
		sensorName180       DisplayString,
		sensorName181       DisplayString,
		sensorName182       DisplayString,
		sensorName183       DisplayString,
		sensorName184       DisplayString,
		sensorName185       DisplayString,
		sensorName186       DisplayString,
		sensorName187       DisplayString,
		sensorName188       DisplayString,
		sensorName189       DisplayString,
		sensorName190       DisplayString,
		sensorName191       DisplayString,
		sensorName192       DisplayString,
		sensorName193       DisplayString,
		sensorName194       DisplayString,
		sensorName195       DisplayString,
		sensorName196       DisplayString,
		sensorName197       DisplayString,
		sensorName198       DisplayString,
		sensorName199       DisplayString,
		sensorName200       DisplayString,
		sensorName201       DisplayString,
		sensorName202       DisplayString,
		sensorName203       DisplayString,
		sensorName204       DisplayString,
		sensorName205       DisplayString,
		sensorName206       DisplayString,
		sensorName207       DisplayString,
		sensorName208       DisplayString,
		sensorName209       DisplayString,
		sensorName210       DisplayString,
		sensorName211       DisplayString,
		sensorName212       DisplayString,
		sensorName213       DisplayString,
		sensorName214       DisplayString,
		sensorName215       DisplayString,
		sensorName216       DisplayString,
		sensorName217       DisplayString,
		sensorName218       DisplayString,
		sensorName219       DisplayString,
		sensorName220       DisplayString,
		sensorName221       DisplayString,
		sensorName222       DisplayString,
		sensorName223       DisplayString,
		sensorName224       DisplayString,
		sensorName225       DisplayString,
		sensorName226       DisplayString,
		sensorName227       DisplayString,
		sensorName228       DisplayString,
		sensorName229       DisplayString,
		sensorName230       DisplayString,
		sensorName231       DisplayString,
		sensorName232       DisplayString,
		sensorName233       DisplayString,
		sensorName234       DisplayString,
		sensorName235       DisplayString,
		sensorName236       DisplayString,
		sensorName237       DisplayString,
		sensorName238       DisplayString,
		sensorName239       DisplayString,
		sensorName240       DisplayString,
		sensorName241       DisplayString,
		sensorName242       DisplayString,
		sensorName243       DisplayString,
		sensorName244       DisplayString,
		sensorName245       DisplayString,
		sensorName246       DisplayString,
		sensorName247       DisplayString,
		sensorName248       DisplayString,
		sensorName249       DisplayString,
		sensorName250       DisplayString,
		sensorName251       DisplayString,
		sensorName252       DisplayString,
		sensorName253       DisplayString,
		sensorName254       DisplayString,
		sensorName255       DisplayString,
		sensorName256       DisplayString
	}
	sensorlistInfoIndex  OBJECT-TYPE
		SYNTAX 			Integer32
		MAX-ACCESS		read-only
		STATUS			current
		DESCRIPTION 
		"  
			The index value which uniquely identifies 
			the interface to which this entry is applicable.
		"
		::= {sensorlistInfoEntry 1}           
	         
	sensorName1 OBJECT-TYPE
		SYNTAX 			DisplayString 
		MAX-ACCESS		read-only
		STATUS			current
		DESCRIPTION 
			""
		::= {sensorlistInfoEntry 2} 
		
	sensorName2	OBJECT-TYPE
	  SYNTAX    DisplayString 
	  MAX-ACCESS  read-only
	  STATUS   current
	  DESCRIPTION 
	   ""
	  ::= {sensorlistInfoEntry 3}
	sensorName3 OBJECT-TYPE
	  SYNTAX    DisplayString 
	  MAX-ACCESS  read-only
	  STATUS   current
	  DESCRIPTION 
	   ""
	  ::= {sensorlistInfoEntry 4}
	sensorName4 OBJECT-TYPE
	  SYNTAX    DisplayString 
	  MAX-ACCESS  read-only
	  STATUS   current
	  DESCRIPTION 
	   ""
	  ::= {sensorlistInfoEntry 5}
	sensorName5 OBJECT-TYPE
	  SYNTAX    DisplayString 
	  MAX-ACCESS  read-only
	  STATUS   current
	  DESCRIPTION 
	   ""
	  ::= {sensorlistInfoEntry 6}
	sensorName6 OBJECT-TYPE
	  SYNTAX    DisplayString 
	  MAX-ACCESS  read-only
	  STATUS   current
	  DESCRIPTION 
	   ""
	  ::= {sensorlistInfoEntry 7}
	sensorName7 OBJECT-TYPE
	  SYNTAX    DisplayString 
	  MAX-ACCESS  read-only
	  STATUS   current
	  DESCRIPTION 
	   ""
	  ::= {sensorlistInfoEntry 8}
	sensorName8 OBJECT-TYPE
	  SYNTAX    DisplayString 
	  MAX-ACCESS  read-only
	  STATUS   current
	  DESCRIPTION 
	   ""
	  ::= {sensorlistInfoEntry 9}
	sensorName9 OBJECT-TYPE
	  SYNTAX    DisplayString 
	  MAX-ACCESS  read-only
	  STATUS   current
	  DESCRIPTION 
	   ""
	  ::= {sensorlistInfoEntry 10}
	sensorName10 OBJECT-TYPE
	  SYNTAX    DisplayString 
	  MAX-ACCESS  read-only
	  STATUS   current
	  DESCRIPTION 
	   ""
	  ::= {sensorlistInfoEntry 11}
	sensorName11 OBJECT-TYPE
	  SYNTAX    DisplayString 
	  MAX-ACCESS  read-only
	  STATUS   current
	  DESCRIPTION 
	   ""
	  ::= {sensorlistInfoEntry 12}
	sensorName12 OBJECT-TYPE
	  SYNTAX    DisplayString 
	  MAX-ACCESS  read-only
	  STATUS   current
	  DESCRIPTION 
	   ""
	  ::= {sensorlistInfoEntry 13}
	sensorName13 OBJECT-TYPE
	  SYNTAX    DisplayString 
	  MAX-ACCESS  read-only
	  STATUS   current
	  DESCRIPTION 
	   ""
	  ::= {sensorlistInfoEntry 14}
	sensorName14 OBJECT-TYPE
	  SYNTAX    DisplayString 
	  MAX-ACCESS  read-only
	  STATUS   current
	  DESCRIPTION 
	   ""
	  ::= {sensorlistInfoEntry 15}
	sensorName15 OBJECT-TYPE
	  SYNTAX    DisplayString 
	  MAX-ACCESS  read-only
	  STATUS   current
	  DESCRIPTION 
	   ""
	  ::= {sensorlistInfoEntry 16}
	sensorName16 OBJECT-TYPE
	  SYNTAX    DisplayString 
	  MAX-ACCESS  read-only
	  STATUS   current
	  DESCRIPTION 
	   ""
	  ::= {sensorlistInfoEntry 17}
	sensorName17 OBJECT-TYPE
	  SYNTAX    DisplayString 
	  MAX-ACCESS  read-only
	  STATUS   current
	  DESCRIPTION 
	   ""
	  ::= {sensorlistInfoEntry 18}
	sensorName18 OBJECT-TYPE
	  SYNTAX    DisplayString 
	  MAX-ACCESS  read-only
	  STATUS   current
	  DESCRIPTION 
	   ""
	  ::= {sensorlistInfoEntry 19}
	sensorName19 OBJECT-TYPE
	  SYNTAX    DisplayString 
	  MAX-ACCESS  read-only
	  STATUS   current
	  DESCRIPTION 
	   ""
	  ::= {sensorlistInfoEntry 20}
	  
	sensorName20 OBJECT-TYPE
	  SYNTAX    DisplayString 
	  MAX-ACCESS  read-only
	  STATUS   current
	  DESCRIPTION 
	   ""
	  ::= {sensorlistInfoEntry 21}
	sensorName21 OBJECT-TYPE
	  SYNTAX    DisplayString 
	  MAX-ACCESS  read-only
	  STATUS   current
	  DESCRIPTION 
	   ""
	  ::= {sensorlistInfoEntry 22}
	sensorName22 OBJECT-TYPE
	  SYNTAX    DisplayString 
	  MAX-ACCESS  read-only
	  STATUS   current
	  DESCRIPTION 
	   ""
	  ::= {sensorlistInfoEntry 23}
	sensorName23 OBJECT-TYPE
	  SYNTAX    DisplayString 
	  MAX-ACCESS  read-only
	  STATUS   current
	  DESCRIPTION 
	   ""
	  ::= {sensorlistInfoEntry 24}
	sensorName24 OBJECT-TYPE
	  SYNTAX    DisplayString 
	  MAX-ACCESS  read-only
	  STATUS   current
	  DESCRIPTION 
	   ""
	  ::= {sensorlistInfoEntry 25}
	sensorName25 OBJECT-TYPE
	  SYNTAX    DisplayString 
	  MAX-ACCESS  read-only
	  STATUS   current
	  DESCRIPTION 
	   ""
	  ::= {sensorlistInfoEntry 26}
	sensorName26 OBJECT-TYPE
	  SYNTAX    DisplayString 
	  MAX-ACCESS  read-only
	  STATUS   current
	  DESCRIPTION 
	   ""
	  ::= {sensorlistInfoEntry 27}
	sensorName27 OBJECT-TYPE
	  SYNTAX    DisplayString 
	  MAX-ACCESS  read-only
	  STATUS   current
	  DESCRIPTION 
	   ""
	  ::= {sensorlistInfoEntry 28}
	sensorName28 OBJECT-TYPE
	  SYNTAX    DisplayString 
	  MAX-ACCESS  read-only
	  STATUS   current
	  DESCRIPTION 
	   ""
	  ::= {sensorlistInfoEntry 29}
	sensorName29 OBJECT-TYPE
	  SYNTAX    DisplayString 
	  MAX-ACCESS  read-only
	  STATUS   current
	  DESCRIPTION 
	   ""
	  ::= {sensorlistInfoEntry 30}
	 
	  
	sensorName30 OBJECT-TYPE
	  SYNTAX    DisplayString 
	  MAX-ACCESS  read-only
	  STATUS   current
	  DESCRIPTION 
	   ""
	  ::= {sensorlistInfoEntry 31}
	sensorName31 OBJECT-TYPE
	  SYNTAX    DisplayString 
	  MAX-ACCESS  read-only
	  STATUS   current
	  DESCRIPTION 
	   ""
	  ::= {sensorlistInfoEntry 32}
	sensorName32 OBJECT-TYPE
	  SYNTAX    DisplayString 
	  MAX-ACCESS  read-only
	  STATUS   current
	  DESCRIPTION 
	   ""
	  ::= {sensorlistInfoEntry 33}
	sensorName33 OBJECT-TYPE
	  SYNTAX    DisplayString 
	  MAX-ACCESS  read-only
	  STATUS   current
	  DESCRIPTION 
	   ""
	  ::= {sensorlistInfoEntry 34}
	sensorName34 OBJECT-TYPE
	  SYNTAX    DisplayString 
	  MAX-ACCESS  read-only
	  STATUS   current
	  DESCRIPTION 
	   ""
	  ::= {sensorlistInfoEntry 35}
	sensorName35 OBJECT-TYPE
	  SYNTAX    DisplayString 
	  MAX-ACCESS  read-only
	  STATUS   current
	  DESCRIPTION 
	   ""
	  ::= {sensorlistInfoEntry 36}
	sensorName36 OBJECT-TYPE
	  SYNTAX    DisplayString 
	  MAX-ACCESS  read-only
	  STATUS   current
	  DESCRIPTION 
	   ""
	  ::= {sensorlistInfoEntry 37}
	sensorName37 OBJECT-TYPE
	  SYNTAX    DisplayString 
	  MAX-ACCESS  read-only
	  STATUS   current
	  DESCRIPTION 
	   ""
	  ::= {sensorlistInfoEntry 38}
	sensorName38 OBJECT-TYPE
	  SYNTAX    DisplayString 
	  MAX-ACCESS  read-only
	  STATUS   current
	  DESCRIPTION 
	   ""
	  ::= {sensorlistInfoEntry 39}
	sensorName39 OBJECT-TYPE
	  SYNTAX    DisplayString 
	  MAX-ACCESS  read-only
	  STATUS   current
	  DESCRIPTION 
	   ""
	  ::= {sensorlistInfoEntry 40}


	sensorName40 OBJECT-TYPE
	  SYNTAX    DisplayString 
	  MAX-ACCESS  read-only
	  STATUS   current
	  DESCRIPTION 
	   ""
	  ::= {sensorlistInfoEntry 41}
	sensorName41 OBJECT-TYPE
	  SYNTAX    DisplayString 
	  MAX-ACCESS  read-only
	  STATUS   current
	  DESCRIPTION 
	   ""
	  ::= {sensorlistInfoEntry 42}
	sensorName42 OBJECT-TYPE
	  SYNTAX    DisplayString 
	  MAX-ACCESS  read-only
	  STATUS   current
	  DESCRIPTION 
	   ""
	  ::= {sensorlistInfoEntry 43}
	sensorName43 OBJECT-TYPE
	  SYNTAX    DisplayString 
	  MAX-ACCESS  read-only
	  STATUS   current
	  DESCRIPTION 
	   ""
	  ::= {sensorlistInfoEntry 44}
	sensorName44 OBJECT-TYPE
	  SYNTAX    DisplayString 
	  MAX-ACCESS  read-only
	  STATUS   current
	  DESCRIPTION 
	   ""
	  ::= {sensorlistInfoEntry 45}
	sensorName45 OBJECT-TYPE
	  SYNTAX    DisplayString 
	  MAX-ACCESS  read-only
	  STATUS   current
	  DESCRIPTION 
	   ""
	  ::= {sensorlistInfoEntry 46}
	sensorName46 OBJECT-TYPE
	  SYNTAX    DisplayString 
	  MAX-ACCESS  read-only
	  STATUS   current
	  DESCRIPTION 
	   ""
	  ::= {sensorlistInfoEntry 47}
	sensorName47 OBJECT-TYPE
	  SYNTAX    DisplayString 
	  MAX-ACCESS  read-only
	  STATUS   current
	  DESCRIPTION 
	   ""
	  ::= {sensorlistInfoEntry 48}
	sensorName48 OBJECT-TYPE
	  SYNTAX    DisplayString 
	  MAX-ACCESS  read-only
	  STATUS   current
	  DESCRIPTION 
	   ""
	  ::= {sensorlistInfoEntry 49}
	sensorName49 OBJECT-TYPE
	  SYNTAX    DisplayString 
	  MAX-ACCESS  read-only
	  STATUS   current
	  DESCRIPTION 
	   ""
	  ::= {sensorlistInfoEntry 50}
	  
	  
	sensorName50 OBJECT-TYPE
	  SYNTAX    DisplayString 
	  MAX-ACCESS  read-only
	  STATUS   current
	  DESCRIPTION 
	   ""
	  ::= {sensorlistInfoEntry 51}
	sensorName51 OBJECT-TYPE
	  SYNTAX    DisplayString 
	  MAX-ACCESS  read-only
	  STATUS   current
	  DESCRIPTION 
	   ""
	  ::= {sensorlistInfoEntry 52}
	sensorName52 OBJECT-TYPE
	  SYNTAX    DisplayString 
	  MAX-ACCESS  read-only
	  STATUS   current
	  DESCRIPTION 
	   ""
	  ::= {sensorlistInfoEntry 53}
	sensorName53 OBJECT-TYPE
	  SYNTAX    DisplayString 
	  MAX-ACCESS  read-only
	  STATUS   current
	  DESCRIPTION 
	   ""
	  ::= {sensorlistInfoEntry 54}
	sensorName54 OBJECT-TYPE
	  SYNTAX    DisplayString 
	  MAX-ACCESS  read-only
	  STATUS   current
	  DESCRIPTION 
	   ""
	  ::= {sensorlistInfoEntry 55}
	sensorName55 OBJECT-TYPE
	  SYNTAX    DisplayString 
	  MAX-ACCESS  read-only
	  STATUS   current
	  DESCRIPTION 
	   ""
	  ::= {sensorlistInfoEntry 56}
	sensorName56 OBJECT-TYPE
	  SYNTAX    DisplayString 
	  MAX-ACCESS  read-only
	  STATUS   current
	  DESCRIPTION 
	   ""
	  ::= {sensorlistInfoEntry 57}
	sensorName57 OBJECT-TYPE
	  SYNTAX    DisplayString 
	  MAX-ACCESS  read-only
	  STATUS   current
	  DESCRIPTION 
	   ""
	  ::= {sensorlistInfoEntry 58}
	sensorName58 OBJECT-TYPE
	  SYNTAX    DisplayString 
	  MAX-ACCESS  read-only
	  STATUS   current
	  DESCRIPTION 
	   ""
	  ::= {sensorlistInfoEntry 59}
	sensorName59 OBJECT-TYPE
	  SYNTAX    DisplayString 
	  MAX-ACCESS  read-only
	  STATUS   current
	  DESCRIPTION 
	   ""
	  ::= {sensorlistInfoEntry 60}
	  
	  
	sensorName60 OBJECT-TYPE
	  SYNTAX    DisplayString 
	  MAX-ACCESS  read-only
	  STATUS   current
	  DESCRIPTION 
	   ""
	  ::= {sensorlistInfoEntry 61}
	sensorName61 OBJECT-TYPE
	  SYNTAX    DisplayString 
	  MAX-ACCESS  read-only
	  STATUS   current
	  DESCRIPTION 
	   ""
	  ::= {sensorlistInfoEntry 62}
	sensorName62 OBJECT-TYPE
	  SYNTAX    DisplayString 
	  MAX-ACCESS  read-only
	  STATUS   current
	  DESCRIPTION 
	   ""
	  ::= {sensorlistInfoEntry 63}
	sensorName63 OBJECT-TYPE
	  SYNTAX    DisplayString 
	  MAX-ACCESS  read-only
	  STATUS   current
	  DESCRIPTION 
	   ""
	  ::= {sensorlistInfoEntry 64}
	sensorName64 OBJECT-TYPE
	  SYNTAX    DisplayString 
	  MAX-ACCESS  read-only
	  STATUS   current
	  DESCRIPTION 
	   ""
	  ::= {sensorlistInfoEntry 65}
	sensorName65 OBJECT-TYPE
	  SYNTAX    DisplayString 
	  MAX-ACCESS  read-only
	  STATUS   current
	  DESCRIPTION 
	   ""
	  ::= {sensorlistInfoEntry 66}
	sensorName66 OBJECT-TYPE
	  SYNTAX    DisplayString 
	  MAX-ACCESS  read-only
	  STATUS   current
	  DESCRIPTION 
	   ""
	  ::= {sensorlistInfoEntry 67}
	sensorName67 OBJECT-TYPE
	  SYNTAX    DisplayString 
	  MAX-ACCESS  read-only
	  STATUS   current
	  DESCRIPTION 
	   ""
	  ::= {sensorlistInfoEntry 68}
	sensorName68 OBJECT-TYPE
	  SYNTAX    DisplayString 
	  MAX-ACCESS  read-only
	  STATUS   current
	  DESCRIPTION 
	   ""
	  ::= {sensorlistInfoEntry 69}
	sensorName69 OBJECT-TYPE
	  SYNTAX    DisplayString 
	  MAX-ACCESS  read-only
	  STATUS   current
	  DESCRIPTION 
	   ""
	  ::= {sensorlistInfoEntry 70}
	  
	 
	sensorName70 OBJECT-TYPE
	  SYNTAX    DisplayString 
	  MAX-ACCESS  read-only
	  STATUS   current
	  DESCRIPTION 
	   ""
	  ::= {sensorlistInfoEntry 71}
	sensorName71 OBJECT-TYPE
	  SYNTAX    DisplayString 
	  MAX-ACCESS  read-only
	  STATUS   current
	  DESCRIPTION 
	   ""
	  ::= {sensorlistInfoEntry 72}
	sensorName72 OBJECT-TYPE
	  SYNTAX    DisplayString 
	  MAX-ACCESS  read-only
	  STATUS   current
	  DESCRIPTION 
	   ""
	  ::= {sensorlistInfoEntry 73}
	sensorName73 OBJECT-TYPE
	  SYNTAX    DisplayString 
	  MAX-ACCESS  read-only
	  STATUS   current
	  DESCRIPTION 
	   ""
	  ::= {sensorlistInfoEntry 74}
	sensorName74 OBJECT-TYPE
	  SYNTAX    DisplayString 
	  MAX-ACCESS  read-only
	  STATUS   current
	  DESCRIPTION 
	   ""
	  ::= {sensorlistInfoEntry 75}
	sensorName75 OBJECT-TYPE
	  SYNTAX    DisplayString 
	  MAX-ACCESS  read-only
	  STATUS   current
	  DESCRIPTION 
	   ""
	  ::= {sensorlistInfoEntry 76}
	sensorName76 OBJECT-TYPE
	  SYNTAX    DisplayString 
	  MAX-ACCESS  read-only
	  STATUS   current
	  DESCRIPTION 
	   ""
	  ::= {sensorlistInfoEntry 77}
	sensorName77 OBJECT-TYPE
	  SYNTAX    DisplayString 
	  MAX-ACCESS  read-only
	  STATUS   current
	  DESCRIPTION 
	   ""
	  ::= {sensorlistInfoEntry 78}
	sensorName78 OBJECT-TYPE
	  SYNTAX    DisplayString 
	  MAX-ACCESS  read-only
	  STATUS   current
	  DESCRIPTION 
	   ""
	  ::= {sensorlistInfoEntry 79}
	sensorName79 OBJECT-TYPE
	  SYNTAX    DisplayString 
	  MAX-ACCESS  read-only
	  STATUS   current
	  DESCRIPTION 
	   ""
	  ::= {sensorlistInfoEntry 80}
	  
	 
	sensorName80 OBJECT-TYPE
	  SYNTAX    DisplayString 
	  MAX-ACCESS  read-only
	  STATUS   current
	  DESCRIPTION 
	   ""
	  ::= {sensorlistInfoEntry 81}
	sensorName81 OBJECT-TYPE
	  SYNTAX    DisplayString 
	  MAX-ACCESS  read-only
	  STATUS   current
	  DESCRIPTION 
	   ""
	  ::= {sensorlistInfoEntry 82}
	sensorName82 OBJECT-TYPE
	  SYNTAX    DisplayString 
	  MAX-ACCESS  read-only
	  STATUS   current
	  DESCRIPTION 
	   ""
	  ::= {sensorlistInfoEntry 83}
	sensorName83 OBJECT-TYPE
	  SYNTAX    DisplayString 
	  MAX-ACCESS  read-only
	  STATUS   current
	  DESCRIPTION 
	   ""
	  ::= {sensorlistInfoEntry 84}
	sensorName84 OBJECT-TYPE
	  SYNTAX    DisplayString 
	  MAX-ACCESS  read-only
	  STATUS   current
	  DESCRIPTION 
	   ""
	  ::= {sensorlistInfoEntry 85}
	sensorName85 OBJECT-TYPE
	  SYNTAX    DisplayString 
	  MAX-ACCESS  read-only
	  STATUS   current
	  DESCRIPTION 
	   ""
	  ::= {sensorlistInfoEntry 86}
	sensorName86 OBJECT-TYPE
	  SYNTAX    DisplayString 
	  MAX-ACCESS  read-only
	  STATUS   current
	  DESCRIPTION 
	   ""
	  ::= {sensorlistInfoEntry 87}
	sensorName87 OBJECT-TYPE
	  SYNTAX    DisplayString 
	  MAX-ACCESS  read-only
	  STATUS   current
	  DESCRIPTION 
	   ""
	  ::= {sensorlistInfoEntry 88}
	sensorName88 OBJECT-TYPE
	  SYNTAX    DisplayString 
	  MAX-ACCESS  read-only
	  STATUS   current
	  DESCRIPTION 
	   ""
	  ::= {sensorlistInfoEntry 89}
	sensorName89 OBJECT-TYPE
	  SYNTAX    DisplayString 
	  MAX-ACCESS  read-only
	  STATUS   current
	  DESCRIPTION 
	   ""
	  ::= {sensorlistInfoEntry 90}
	  
	 
	sensorName90 OBJECT-TYPE
	  SYNTAX    DisplayString 
	  MAX-ACCESS  read-only
	  STATUS   current
	  DESCRIPTION 
	   ""
	  ::= {sensorlistInfoEntry 91}
	sensorName91 OBJECT-TYPE
	  SYNTAX    DisplayString 
	  MAX-ACCESS  read-only
	  STATUS   current
	  DESCRIPTION 
	   ""
	  ::= {sensorlistInfoEntry 92}
	sensorName92 OBJECT-TYPE
	  SYNTAX    DisplayString 
	  MAX-ACCESS  read-only
	  STATUS   current
	  DESCRIPTION 
	   ""
	  ::= {sensorlistInfoEntry 93}
	sensorName93 OBJECT-TYPE
	  SYNTAX    DisplayString 
	  MAX-ACCESS  read-only
	  STATUS   current
	  DESCRIPTION 
	   ""
	  ::= {sensorlistInfoEntry 94}
	sensorName94 OBJECT-TYPE
	  SYNTAX    DisplayString 
	  MAX-ACCESS  read-only
	  STATUS   current
	  DESCRIPTION 
	   ""
	  ::= {sensorlistInfoEntry 95}
	sensorName95 OBJECT-TYPE
	  SYNTAX    DisplayString 
	  MAX-ACCESS  read-only
	  STATUS   current
	  DESCRIPTION 
	   ""
	  ::= {sensorlistInfoEntry 96}
	sensorName96 OBJECT-TYPE
	  SYNTAX    DisplayString 
	  MAX-ACCESS  read-only
	  STATUS   current
	  DESCRIPTION 
	   ""
	  ::= {sensorlistInfoEntry 97}
	sensorName97 OBJECT-TYPE
	  SYNTAX    DisplayString 
	  MAX-ACCESS  read-only
	  STATUS   current
	  DESCRIPTION 
	   ""
	  ::= {sensorlistInfoEntry 98}
	sensorName98 OBJECT-TYPE
	  SYNTAX    DisplayString 
	  MAX-ACCESS  read-only
	  STATUS   current
	  DESCRIPTION 
	   ""
	  ::= {sensorlistInfoEntry 99}
	sensorName99 OBJECT-TYPE
	  SYNTAX    DisplayString 
	  MAX-ACCESS  read-only
	  STATUS   current
	  DESCRIPTION 
	   ""
	  ::= {sensorlistInfoEntry 100}
	  
	 
	sensorName100 OBJECT-TYPE
	  SYNTAX    DisplayString 
	  MAX-ACCESS  read-only
	  STATUS   current
	  DESCRIPTION 
	   ""
	  ::= {sensorlistInfoEntry 101}
	sensorName101 OBJECT-TYPE
	  SYNTAX    DisplayString 
	  MAX-ACCESS  read-only
	  STATUS   current
	  DESCRIPTION 
	   ""
	  ::= {sensorlistInfoEntry 102}
	sensorName102 OBJECT-TYPE
	  SYNTAX    DisplayString 
	  MAX-ACCESS  read-only
	  STATUS   current
	  DESCRIPTION 
	   ""
	  ::= {sensorlistInfoEntry 103}
	sensorName103 OBJECT-TYPE
	  SYNTAX    DisplayString 
	  MAX-ACCESS  read-only
	  STATUS   current
	  DESCRIPTION 
	   ""
	  ::= {sensorlistInfoEntry 104}
	sensorName104 OBJECT-TYPE
	  SYNTAX    DisplayString 
	  MAX-ACCESS  read-only
	  STATUS   current
	  DESCRIPTION 
	   ""
	  ::= {sensorlistInfoEntry 105}
	sensorName105 OBJECT-TYPE
	  SYNTAX    DisplayString 
	  MAX-ACCESS  read-only
	  STATUS   current
	  DESCRIPTION 
	   ""
	  ::= {sensorlistInfoEntry 106}
	sensorName106 OBJECT-TYPE
	  SYNTAX    DisplayString 
	  MAX-ACCESS  read-only
	  STATUS   current
	  DESCRIPTION 
	   ""
	  ::= {sensorlistInfoEntry 107}
	sensorName107 OBJECT-TYPE
	  SYNTAX    DisplayString 
	  MAX-ACCESS  read-only
	  STATUS   current
	  DESCRIPTION 
	   ""
	  ::= {sensorlistInfoEntry 108}
	sensorName108 OBJECT-TYPE
	  SYNTAX    DisplayString 
	  MAX-ACCESS  read-only
	  STATUS   current
	  DESCRIPTION 
	   ""
	  ::= {sensorlistInfoEntry 109}
	sensorName109 OBJECT-TYPE
	  SYNTAX    DisplayString 
	  MAX-ACCESS  read-only
	  STATUS   current
	  DESCRIPTION 
	   ""
	  ::= {sensorlistInfoEntry 110}
	  
	 
	sensorName110 OBJECT-TYPE
	  SYNTAX    DisplayString 
	  MAX-ACCESS  read-only
	  STATUS   current
	  DESCRIPTION 
	   ""
	  ::= {sensorlistInfoEntry 111}
	sensorName111 OBJECT-TYPE
	  SYNTAX    DisplayString 
	  MAX-ACCESS  read-only
	  STATUS   current
	  DESCRIPTION 
	   ""
	  ::= {sensorlistInfoEntry 112}
	sensorName112 OBJECT-TYPE
	  SYNTAX    DisplayString 
	  MAX-ACCESS  read-only
	  STATUS   current
	  DESCRIPTION 
	   ""
	  ::= {sensorlistInfoEntry 113}
	sensorName113 OBJECT-TYPE
	  SYNTAX    DisplayString 
	  MAX-ACCESS  read-only
	  STATUS   current
	  DESCRIPTION 
	   ""
	  ::= {sensorlistInfoEntry 114}
	sensorName114 OBJECT-TYPE
	  SYNTAX    DisplayString 
	  MAX-ACCESS  read-only
	  STATUS   current
	  DESCRIPTION 
	   ""
	  ::= {sensorlistInfoEntry 115}
	sensorName115 OBJECT-TYPE
	  SYNTAX    DisplayString 
	  MAX-ACCESS  read-only
	  STATUS   current
	  DESCRIPTION 
	   ""
	  ::= {sensorlistInfoEntry 116}
	sensorName116 OBJECT-TYPE
	  SYNTAX    DisplayString 
	  MAX-ACCESS  read-only
	  STATUS   current
	  DESCRIPTION 
	   ""
	  ::= {sensorlistInfoEntry 117}
	sensorName117 OBJECT-TYPE
	  SYNTAX    DisplayString 
	  MAX-ACCESS  read-only
	  STATUS   current
	  DESCRIPTION 
	   ""
	  ::= {sensorlistInfoEntry 118}
	sensorName118 OBJECT-TYPE
	  SYNTAX    DisplayString 
	  MAX-ACCESS  read-only
	  STATUS   current
	  DESCRIPTION 
	   ""
	  ::= {sensorlistInfoEntry 119}
	sensorName119 OBJECT-TYPE
	  SYNTAX    DisplayString 
	  MAX-ACCESS  read-only
	  STATUS   current
	  DESCRIPTION 
	   ""
	  ::= {sensorlistInfoEntry 120}
	  
	 
	sensorName120 OBJECT-TYPE
	  SYNTAX    DisplayString 
	  MAX-ACCESS  read-only
	  STATUS   current
	  DESCRIPTION 
	   ""
	  ::= {sensorlistInfoEntry 121}
	sensorName121 OBJECT-TYPE
	  SYNTAX    DisplayString 
	  MAX-ACCESS  read-only
	  STATUS   current
	  DESCRIPTION 
	   ""
	  ::= {sensorlistInfoEntry 122}
	sensorName122 OBJECT-TYPE
	  SYNTAX    DisplayString 
	  MAX-ACCESS  read-only
	  STATUS   current
	  DESCRIPTION 
	   ""
	  ::= {sensorlistInfoEntry 123}
	sensorName123 OBJECT-TYPE
	  SYNTAX    DisplayString 
	  MAX-ACCESS  read-only
	  STATUS   current
	  DESCRIPTION 
	   ""
	  ::= {sensorlistInfoEntry 124}
	sensorName124 OBJECT-TYPE
	  SYNTAX    DisplayString 
	  MAX-ACCESS  read-only
	  STATUS   current
	  DESCRIPTION 
	   ""
	  ::= {sensorlistInfoEntry 125}
	sensorName125 OBJECT-TYPE
	  SYNTAX    DisplayString 
	  MAX-ACCESS  read-only
	  STATUS   current
	  DESCRIPTION 
	   ""
	  ::= {sensorlistInfoEntry 126}
	sensorName126 OBJECT-TYPE
	  SYNTAX    DisplayString 
	  MAX-ACCESS  read-only
	  STATUS   current
	  DESCRIPTION 
	   ""
	  ::= {sensorlistInfoEntry 127}
	sensorName127 OBJECT-TYPE
	  SYNTAX    DisplayString 
	  MAX-ACCESS  read-only
	  STATUS   current
	  DESCRIPTION 
	   ""
	  ::= {sensorlistInfoEntry 128}
	sensorName128 OBJECT-TYPE
	  SYNTAX    DisplayString 
	  MAX-ACCESS  read-only
	  STATUS   current
	  DESCRIPTION 
	   ""
	  ::= {sensorlistInfoEntry 129}
	sensorName129 OBJECT-TYPE
	  SYNTAX    DisplayString 
	  MAX-ACCESS  read-only
	  STATUS   current
	  DESCRIPTION 
	   ""
	  ::= {sensorlistInfoEntry 130}
	  
	 
	sensorName130 OBJECT-TYPE
	  SYNTAX    DisplayString 
	  MAX-ACCESS  read-only
	  STATUS   current
	  DESCRIPTION 
	   ""
	  ::= {sensorlistInfoEntry 131}
	sensorName131 OBJECT-TYPE
	  SYNTAX    DisplayString 
	  MAX-ACCESS  read-only
	  STATUS   current
	  DESCRIPTION 
	   ""
	  ::= {sensorlistInfoEntry 132}
	sensorName132 OBJECT-TYPE
	  SYNTAX    DisplayString 
	  MAX-ACCESS  read-only
	  STATUS   current
	  DESCRIPTION 
	   ""
	  ::= {sensorlistInfoEntry 133}
	sensorName133 OBJECT-TYPE
	  SYNTAX    DisplayString 
	  MAX-ACCESS  read-only
	  STATUS   current
	  DESCRIPTION 
	   ""
	  ::= {sensorlistInfoEntry 134}
	sensorName134 OBJECT-TYPE
	  SYNTAX    DisplayString 
	  MAX-ACCESS  read-only
	  STATUS   current
	  DESCRIPTION 
	   ""
	  ::= {sensorlistInfoEntry 135}
	sensorName135 OBJECT-TYPE
	  SYNTAX    DisplayString 
	  MAX-ACCESS  read-only
	  STATUS   current
	  DESCRIPTION 
	   ""
	  ::= {sensorlistInfoEntry 136}
	sensorName136 OBJECT-TYPE
	  SYNTAX    DisplayString 
	  MAX-ACCESS  read-only
	  STATUS   current
	  DESCRIPTION 
	   ""
	  ::= {sensorlistInfoEntry 137}
	sensorName137 OBJECT-TYPE
	  SYNTAX    DisplayString 
	  MAX-ACCESS  read-only
	  STATUS   current
	  DESCRIPTION 
	   ""
	  ::= {sensorlistInfoEntry 138}
	sensorName138 OBJECT-TYPE
	  SYNTAX    DisplayString 
	  MAX-ACCESS  read-only
	  STATUS   current
	  DESCRIPTION 
	   ""
	  ::= {sensorlistInfoEntry 139}
	sensorName139 OBJECT-TYPE
	  SYNTAX    DisplayString 
	  MAX-ACCESS  read-only
	  STATUS   current
	  DESCRIPTION 
	   ""
	  ::= {sensorlistInfoEntry 140}
	  
	 
	sensorName140 OBJECT-TYPE
	  SYNTAX    DisplayString 
	  MAX-ACCESS  read-only
	  STATUS   current
	  DESCRIPTION 
	   ""
	  ::= {sensorlistInfoEntry 141}
	sensorName141 OBJECT-TYPE
	  SYNTAX    DisplayString 
	  MAX-ACCESS  read-only
	  STATUS   current
	  DESCRIPTION 
	   ""
	  ::= {sensorlistInfoEntry 142}
	sensorName142 OBJECT-TYPE
	  SYNTAX    DisplayString 
	  MAX-ACCESS  read-only
	  STATUS   current
	  DESCRIPTION 
	   ""
	  ::= {sensorlistInfoEntry 143}
	sensorName143 OBJECT-TYPE
	  SYNTAX    DisplayString 
	  MAX-ACCESS  read-only
	  STATUS   current
	  DESCRIPTION 
	   ""
	  ::= {sensorlistInfoEntry 144}
	sensorName144 OBJECT-TYPE
	  SYNTAX    DisplayString 
	  MAX-ACCESS  read-only
	  STATUS   current
	  DESCRIPTION 
	   ""
	  ::= {sensorlistInfoEntry 145}
	sensorName145 OBJECT-TYPE
	  SYNTAX    DisplayString 
	  MAX-ACCESS  read-only
	  STATUS   current
	  DESCRIPTION 
	   ""
	  ::= {sensorlistInfoEntry 146}
	sensorName146 OBJECT-TYPE
	  SYNTAX    DisplayString 
	  MAX-ACCESS  read-only
	  STATUS   current
	  DESCRIPTION 
	   ""
	  ::= {sensorlistInfoEntry 147}
	sensorName147 OBJECT-TYPE
	  SYNTAX    DisplayString 
	  MAX-ACCESS  read-only
	  STATUS   current
	  DESCRIPTION 
	   ""
	  ::= {sensorlistInfoEntry 148}
	sensorName148 OBJECT-TYPE
	  SYNTAX    DisplayString 
	  MAX-ACCESS  read-only
	  STATUS   current
	  DESCRIPTION 
	   ""
	  ::= {sensorlistInfoEntry 149}
	sensorName149 OBJECT-TYPE
	  SYNTAX    DisplayString 
	  MAX-ACCESS  read-only
	  STATUS   current
	  DESCRIPTION 
	   ""
	  ::= {sensorlistInfoEntry 150}
	  
	 
	sensorName150 OBJECT-TYPE
	  SYNTAX    DisplayString 
	  MAX-ACCESS  read-only
	  STATUS   current
	  DESCRIPTION 
	   ""
	  ::= {sensorlistInfoEntry 151}
	sensorName151 OBJECT-TYPE
	  SYNTAX    DisplayString 
	  MAX-ACCESS  read-only
	  STATUS   current
	  DESCRIPTION 
	   ""
	  ::= {sensorlistInfoEntry 152}
	sensorName152 OBJECT-TYPE
	  SYNTAX    DisplayString 
	  MAX-ACCESS  read-only
	  STATUS   current
	  DESCRIPTION 
	   ""
	  ::= {sensorlistInfoEntry 153}
	sensorName153 OBJECT-TYPE
	  SYNTAX    DisplayString 
	  MAX-ACCESS  read-only
	  STATUS   current
	  DESCRIPTION 
	   ""
	  ::= {sensorlistInfoEntry 154}
	sensorName154 OBJECT-TYPE
	  SYNTAX    DisplayString 
	  MAX-ACCESS  read-only
	  STATUS   current
	  DESCRIPTION 
	   ""
	  ::= {sensorlistInfoEntry 155}
	sensorName155 OBJECT-TYPE
	  SYNTAX    DisplayString 
	  MAX-ACCESS  read-only
	  STATUS   current
	  DESCRIPTION 
	   ""
	  ::= {sensorlistInfoEntry 156}
	sensorName156 OBJECT-TYPE
	  SYNTAX    DisplayString 
	  MAX-ACCESS  read-only
	  STATUS   current
	  DESCRIPTION 
	   ""
	  ::= {sensorlistInfoEntry 157}
	sensorName157 OBJECT-TYPE
	  SYNTAX    DisplayString 
	  MAX-ACCESS  read-only
	  STATUS   current
	  DESCRIPTION 
	   ""
	  ::= {sensorlistInfoEntry 158}
	sensorName158 OBJECT-TYPE
	  SYNTAX    DisplayString 
	  MAX-ACCESS  read-only
	  STATUS   current
	  DESCRIPTION 
	   ""
	  ::= {sensorlistInfoEntry 159}
	sensorName159 OBJECT-TYPE
	  SYNTAX    DisplayString 
	  MAX-ACCESS  read-only
	  STATUS   current
	  DESCRIPTION 
	   ""
	  ::= {sensorlistInfoEntry 160}
	  
	 
	sensorName160 OBJECT-TYPE
	  SYNTAX    DisplayString 
	  MAX-ACCESS  read-only
	  STATUS   current
	  DESCRIPTION 
	   ""
	  ::= {sensorlistInfoEntry 161}
	sensorName161 OBJECT-TYPE
	  SYNTAX    DisplayString 
	  MAX-ACCESS  read-only
	  STATUS   current
	  DESCRIPTION 
	   ""
	  ::= {sensorlistInfoEntry 162}
	sensorName162 OBJECT-TYPE
	  SYNTAX    DisplayString 
	  MAX-ACCESS  read-only
	  STATUS   current
	  DESCRIPTION 
	   ""
	  ::= {sensorlistInfoEntry 163}
	sensorName163 OBJECT-TYPE
	  SYNTAX    DisplayString 
	  MAX-ACCESS  read-only
	  STATUS   current
	  DESCRIPTION 
	   ""
	  ::= {sensorlistInfoEntry 164}
	sensorName164 OBJECT-TYPE
	  SYNTAX    DisplayString 
	  MAX-ACCESS  read-only
	  STATUS   current
	  DESCRIPTION 
	   ""
	  ::= {sensorlistInfoEntry 165}
	sensorName165 OBJECT-TYPE
	  SYNTAX    DisplayString 
	  MAX-ACCESS  read-only
	  STATUS   current
	  DESCRIPTION 
	   ""
	  ::= {sensorlistInfoEntry 166}
	sensorName166 OBJECT-TYPE
	  SYNTAX    DisplayString 
	  MAX-ACCESS  read-only
	  STATUS   current
	  DESCRIPTION 
	   ""
	  ::= {sensorlistInfoEntry 167}
	sensorName167 OBJECT-TYPE
	  SYNTAX    DisplayString 
	  MAX-ACCESS  read-only
	  STATUS   current
	  DESCRIPTION 
	   ""
	  ::= {sensorlistInfoEntry 168}
	sensorName168 OBJECT-TYPE
	  SYNTAX    DisplayString 
	  MAX-ACCESS  read-only
	  STATUS   current
	  DESCRIPTION 
	   ""
	  ::= {sensorlistInfoEntry 169}
	sensorName169 OBJECT-TYPE
	  SYNTAX    DisplayString 
	  MAX-ACCESS  read-only
	  STATUS   current
	  DESCRIPTION 
	   ""
	  ::= {sensorlistInfoEntry 170}
	  
	 
	sensorName170 OBJECT-TYPE
	  SYNTAX    DisplayString 
	  MAX-ACCESS  read-only
	  STATUS   current
	  DESCRIPTION 
	   ""
	  ::= {sensorlistInfoEntry 171}
	sensorName171 OBJECT-TYPE
	  SYNTAX    DisplayString 
	  MAX-ACCESS  read-only
	  STATUS   current
	  DESCRIPTION 
	   ""
	  ::= {sensorlistInfoEntry 172}
	sensorName172 OBJECT-TYPE
	  SYNTAX    DisplayString 
	  MAX-ACCESS  read-only
	  STATUS   current
	  DESCRIPTION 
	   ""
	  ::= {sensorlistInfoEntry 173}
	sensorName173 OBJECT-TYPE
	  SYNTAX    DisplayString 
	  MAX-ACCESS  read-only
	  STATUS   current
	  DESCRIPTION 
	   ""
	  ::= {sensorlistInfoEntry 174}
	sensorName174 OBJECT-TYPE
	  SYNTAX    DisplayString 
	  MAX-ACCESS  read-only
	  STATUS   current
	  DESCRIPTION 
	   ""
	  ::= {sensorlistInfoEntry 175}
	sensorName175 OBJECT-TYPE
	  SYNTAX    DisplayString 
	  MAX-ACCESS  read-only
	  STATUS   current
	  DESCRIPTION 
	   ""
	  ::= {sensorlistInfoEntry 176}
	sensorName176 OBJECT-TYPE
	  SYNTAX    DisplayString 
	  MAX-ACCESS  read-only
	  STATUS   current
	  DESCRIPTION 
	   ""
	  ::= {sensorlistInfoEntry 177}
	sensorName177 OBJECT-TYPE
	  SYNTAX    DisplayString 
	  MAX-ACCESS  read-only
	  STATUS   current
	  DESCRIPTION 
	   ""
	  ::= {sensorlistInfoEntry 178}
	sensorName178 OBJECT-TYPE
	  SYNTAX    DisplayString 
	  MAX-ACCESS  read-only
	  STATUS   current
	  DESCRIPTION 
	   ""
	  ::= {sensorlistInfoEntry 179}
	sensorName179 OBJECT-TYPE
	  SYNTAX    DisplayString 
	  MAX-ACCESS  read-only
	  STATUS   current
	  DESCRIPTION 
	   ""
	  ::= {sensorlistInfoEntry 180}
	 
	 
	sensorName180 OBJECT-TYPE
	  SYNTAX    DisplayString 
	  MAX-ACCESS  read-only
	  STATUS   current
	  DESCRIPTION 
	   ""
	  ::= {sensorlistInfoEntry 181}
	sensorName181 OBJECT-TYPE
	  SYNTAX    DisplayString 
	  MAX-ACCESS  read-only
	  STATUS   current
	  DESCRIPTION 
	   ""
	  ::= {sensorlistInfoEntry 182}
	sensorName182 OBJECT-TYPE
	  SYNTAX    DisplayString 
	  MAX-ACCESS  read-only
	  STATUS   current
	  DESCRIPTION 
	   ""
	  ::= {sensorlistInfoEntry 183}
	sensorName183 OBJECT-TYPE
	  SYNTAX    DisplayString 
	  MAX-ACCESS  read-only
	  STATUS   current
	  DESCRIPTION 
	   ""
	  ::= {sensorlistInfoEntry 184}
	sensorName184 OBJECT-TYPE
	  SYNTAX    DisplayString 
	  MAX-ACCESS  read-only
	  STATUS   current
	  DESCRIPTION 
	   ""
	  ::= {sensorlistInfoEntry 185}
	sensorName185 OBJECT-TYPE
	  SYNTAX    DisplayString 
	  MAX-ACCESS  read-only
	  STATUS   current
	  DESCRIPTION 
	   ""
	  ::= {sensorlistInfoEntry 186}
	sensorName186 OBJECT-TYPE
	  SYNTAX    DisplayString 
	  MAX-ACCESS  read-only
	  STATUS   current
	  DESCRIPTION 
	   ""
	  ::= {sensorlistInfoEntry 187}
	sensorName187 OBJECT-TYPE
	  SYNTAX    DisplayString 
	  MAX-ACCESS  read-only
	  STATUS   current
	  DESCRIPTION 
	   ""
	  ::= {sensorlistInfoEntry 188}
	sensorName188 OBJECT-TYPE
	  SYNTAX    DisplayString 
	  MAX-ACCESS  read-only
	  STATUS   current
	  DESCRIPTION 
	   ""
	  ::= {sensorlistInfoEntry 189}
	sensorName189 OBJECT-TYPE
	  SYNTAX    DisplayString 
	  MAX-ACCESS  read-only
	  STATUS   current
	  DESCRIPTION 
	   ""
	  ::= {sensorlistInfoEntry 190}
	  
	 
	sensorName190 OBJECT-TYPE
	  SYNTAX    DisplayString 
	  MAX-ACCESS  read-only
	  STATUS   current
	  DESCRIPTION 
	   ""
	  ::= {sensorlistInfoEntry 191}
	sensorName191 OBJECT-TYPE
	  SYNTAX    DisplayString 
	  MAX-ACCESS  read-only
	  STATUS   current
	  DESCRIPTION 
	   ""
	  ::= {sensorlistInfoEntry 192}
	sensorName192 OBJECT-TYPE
	  SYNTAX    DisplayString 
	  MAX-ACCESS  read-only
	  STATUS   current
	  DESCRIPTION 
	   ""
	  ::= {sensorlistInfoEntry 193}
	sensorName193 OBJECT-TYPE
	  SYNTAX    DisplayString 
	  MAX-ACCESS  read-only
	  STATUS   current
	  DESCRIPTION 
	   ""
	  ::= {sensorlistInfoEntry 194}
	sensorName194 OBJECT-TYPE
	  SYNTAX    DisplayString 
	  MAX-ACCESS  read-only
	  STATUS   current
	  DESCRIPTION 
	   ""
	  ::= {sensorlistInfoEntry 195}
	sensorName195 OBJECT-TYPE
	  SYNTAX    DisplayString 
	  MAX-ACCESS  read-only
	  STATUS   current
	  DESCRIPTION 
	   ""
	  ::= {sensorlistInfoEntry 196}
	sensorName196 OBJECT-TYPE
	  SYNTAX    DisplayString 
	  MAX-ACCESS  read-only
	  STATUS   current
	  DESCRIPTION 
	   ""
	  ::= {sensorlistInfoEntry 197}
	sensorName197 OBJECT-TYPE
	  SYNTAX    DisplayString 
	  MAX-ACCESS  read-only
	  STATUS   current
	  DESCRIPTION 
	   ""
	  ::= {sensorlistInfoEntry 198}
	sensorName198 OBJECT-TYPE
	  SYNTAX    DisplayString 
	  MAX-ACCESS  read-only
	  STATUS   current
	  DESCRIPTION 
	   ""
	  ::= {sensorlistInfoEntry 199}
	sensorName199 OBJECT-TYPE
	  SYNTAX    DisplayString 
	  MAX-ACCESS  read-only
	  STATUS   current
	  DESCRIPTION 
	   ""
	  ::= {sensorlistInfoEntry 200}
	sensorName200 OBJECT-TYPE
	  SYNTAX    DisplayString 
	  MAX-ACCESS  read-only
	  STATUS   current
	  DESCRIPTION 
	   ""
	  ::= {sensorlistInfoEntry 201}
	sensorName201 OBJECT-TYPE
	  SYNTAX    DisplayString 
	  MAX-ACCESS  read-only
	  STATUS   current
	  DESCRIPTION 
	   ""
	  ::= {sensorlistInfoEntry 202}
	sensorName202 OBJECT-TYPE
	  SYNTAX    DisplayString 
	  MAX-ACCESS  read-only
	  STATUS   current
	  DESCRIPTION 
	   ""
	  ::= {sensorlistInfoEntry 203}
	sensorName203 OBJECT-TYPE
	  SYNTAX    DisplayString 
	  MAX-ACCESS  read-only
	  STATUS   current
	  DESCRIPTION 
	   ""
	  ::= {sensorlistInfoEntry 204}
	sensorName204 OBJECT-TYPE
	  SYNTAX    DisplayString 
	  MAX-ACCESS  read-only
	  STATUS   current
	  DESCRIPTION 
	   ""
	  ::= {sensorlistInfoEntry 205}
	sensorName205 OBJECT-TYPE
	  SYNTAX    DisplayString 
	  MAX-ACCESS  read-only
	  STATUS   current
	  DESCRIPTION 
	   ""
	  ::= {sensorlistInfoEntry 206}
	sensorName206 OBJECT-TYPE
	  SYNTAX    DisplayString 
	  MAX-ACCESS  read-only
	  STATUS   current
	  DESCRIPTION 
	   ""
	  ::= {sensorlistInfoEntry 207}
	sensorName207 OBJECT-TYPE
	  SYNTAX    DisplayString 
	  MAX-ACCESS  read-only
	  STATUS   current
	  DESCRIPTION 
	   ""
	  ::= {sensorlistInfoEntry 208}
	sensorName208 OBJECT-TYPE
	  SYNTAX    DisplayString 
	  MAX-ACCESS  read-only
	  STATUS   current
	  DESCRIPTION 
	   ""
	  ::= {sensorlistInfoEntry 209}
	sensorName209 OBJECT-TYPE
	  SYNTAX    DisplayString 
	  MAX-ACCESS  read-only
	  STATUS   current
	  DESCRIPTION 
	   ""
	  ::= {sensorlistInfoEntry 210}
	sensorName210 OBJECT-TYPE
	  SYNTAX    DisplayString 
	  MAX-ACCESS  read-only
	  STATUS   current
	  DESCRIPTION 
	   ""
	  ::= {sensorlistInfoEntry 211}
	sensorName211 OBJECT-TYPE
	  SYNTAX    DisplayString 
	  MAX-ACCESS  read-only
	  STATUS   current
	  DESCRIPTION 
	   ""
	  ::= {sensorlistInfoEntry 212}
	sensorName212 OBJECT-TYPE
	  SYNTAX    DisplayString 
	  MAX-ACCESS  read-only
	  STATUS   current
	  DESCRIPTION 
	   ""
	  ::= {sensorlistInfoEntry 213}
	sensorName213 OBJECT-TYPE
	  SYNTAX    DisplayString 
	  MAX-ACCESS  read-only
	  STATUS   current
	  DESCRIPTION 
	   ""
	  ::= {sensorlistInfoEntry 214}
	sensorName214 OBJECT-TYPE
	  SYNTAX    DisplayString 
	  MAX-ACCESS  read-only
	  STATUS   current
	  DESCRIPTION 
	   ""
	  ::= {sensorlistInfoEntry 215}
	sensorName215 OBJECT-TYPE
	  SYNTAX    DisplayString 
	  MAX-ACCESS  read-only
	  STATUS   current
	  DESCRIPTION 
	   ""
	  ::= {sensorlistInfoEntry 216}
	sensorName216 OBJECT-TYPE
	  SYNTAX    DisplayString 
	  MAX-ACCESS  read-only
	  STATUS   current
	  DESCRIPTION 
	   ""
	  ::= {sensorlistInfoEntry 217}
	sensorName217 OBJECT-TYPE
	  SYNTAX    DisplayString 
	  MAX-ACCESS  read-only
	  STATUS   current
	  DESCRIPTION 
	   ""
	  ::= {sensorlistInfoEntry 218}
	sensorName218 OBJECT-TYPE
	  SYNTAX    DisplayString 
	  MAX-ACCESS  read-only
	  STATUS   current
	  DESCRIPTION 
	   ""
	  ::= {sensorlistInfoEntry 219}
	sensorName219 OBJECT-TYPE
	  SYNTAX    DisplayString 
	  MAX-ACCESS  read-only
	  STATUS   current
	  DESCRIPTION 
	   ""
	  ::= {sensorlistInfoEntry 220}
	sensorName220 OBJECT-TYPE
	  SYNTAX    DisplayString 
	  MAX-ACCESS  read-only
	  STATUS   current
	  DESCRIPTION 
	   ""
	  ::= {sensorlistInfoEntry 221}
	sensorName221 OBJECT-TYPE
	  SYNTAX    DisplayString 
	  MAX-ACCESS  read-only
	  STATUS   current
	  DESCRIPTION 
	   ""
	  ::= {sensorlistInfoEntry 222}
	sensorName222 OBJECT-TYPE
	  SYNTAX    DisplayString 
	  MAX-ACCESS  read-only
	  STATUS   current
	  DESCRIPTION 
	   ""
	  ::= {sensorlistInfoEntry 223}
	sensorName223 OBJECT-TYPE
	  SYNTAX    DisplayString 
	  MAX-ACCESS  read-only
	  STATUS   current
	  DESCRIPTION 
	   ""
	  ::= {sensorlistInfoEntry 224}
	sensorName224 OBJECT-TYPE
	  SYNTAX    DisplayString 
	  MAX-ACCESS  read-only
	  STATUS   current
	  DESCRIPTION 
	   ""
	  ::= {sensorlistInfoEntry 225}
	sensorName225 OBJECT-TYPE
	  SYNTAX    DisplayString 
	  MAX-ACCESS  read-only
	  STATUS   current
	  DESCRIPTION 
	   ""
	  ::= {sensorlistInfoEntry 226}
	sensorName226 OBJECT-TYPE
	  SYNTAX    DisplayString 
	  MAX-ACCESS  read-only
	  STATUS   current
	  DESCRIPTION 
	   ""
	  ::= {sensorlistInfoEntry 227}
	sensorName227 OBJECT-TYPE
	  SYNTAX    DisplayString 
	  MAX-ACCESS  read-only
	  STATUS   current
	  DESCRIPTION 
	   ""
	  ::= {sensorlistInfoEntry 228}
	sensorName228 OBJECT-TYPE
	  SYNTAX    DisplayString 
	  MAX-ACCESS  read-only
	  STATUS   current
	  DESCRIPTION 
	   ""
	  ::= {sensorlistInfoEntry 229}
	sensorName229 OBJECT-TYPE
	  SYNTAX    DisplayString 
	  MAX-ACCESS  read-only
	  STATUS   current
	  DESCRIPTION 
	   ""
	  ::= {sensorlistInfoEntry 230}
	sensorName230 OBJECT-TYPE
	  SYNTAX    DisplayString 
	  MAX-ACCESS  read-only
	  STATUS   current
	  DESCRIPTION 
	   ""
	  ::= {sensorlistInfoEntry 231}
	sensorName231 OBJECT-TYPE
	  SYNTAX    DisplayString 
	  MAX-ACCESS  read-only
	  STATUS   current
	  DESCRIPTION 
	   ""
	  ::= {sensorlistInfoEntry 232}
	sensorName232 OBJECT-TYPE
	  SYNTAX    DisplayString 
	  MAX-ACCESS  read-only
	  STATUS   current
	  DESCRIPTION 
	   ""
	  ::= {sensorlistInfoEntry 233}
	sensorName233 OBJECT-TYPE
	  SYNTAX    DisplayString 
	  MAX-ACCESS  read-only
	  STATUS   current
	  DESCRIPTION 
	   ""
	  ::= {sensorlistInfoEntry 234}
	sensorName234 OBJECT-TYPE
	  SYNTAX    DisplayString 
	  MAX-ACCESS  read-only
	  STATUS   current
	  DESCRIPTION 
	   ""
	  ::= {sensorlistInfoEntry 235}
	sensorName235 OBJECT-TYPE
	  SYNTAX    DisplayString 
	  MAX-ACCESS  read-only
	  STATUS   current
	  DESCRIPTION 
	   ""
	  ::= {sensorlistInfoEntry 236}
	sensorName236 OBJECT-TYPE
	  SYNTAX    DisplayString 
	  MAX-ACCESS  read-only
	  STATUS   current
	  DESCRIPTION 
	   ""
	  ::= {sensorlistInfoEntry 237}
	sensorName237 OBJECT-TYPE
	  SYNTAX    DisplayString 
	  MAX-ACCESS  read-only
	  STATUS   current
	  DESCRIPTION 
	   ""
	  ::= {sensorlistInfoEntry 238}
	sensorName238 OBJECT-TYPE
	  SYNTAX    DisplayString 
	  MAX-ACCESS  read-only
	  STATUS   current
	  DESCRIPTION 
	   ""
	  ::= {sensorlistInfoEntry 239}
	sensorName239 OBJECT-TYPE
	  SYNTAX    DisplayString 
	  MAX-ACCESS  read-only
	  STATUS   current
	  DESCRIPTION 
	   ""
	  ::= {sensorlistInfoEntry 240}
	sensorName240 OBJECT-TYPE
	  SYNTAX    DisplayString 
	  MAX-ACCESS  read-only
	  STATUS   current
	  DESCRIPTION 
	   ""
	  ::= {sensorlistInfoEntry 241}
	sensorName241 OBJECT-TYPE
	  SYNTAX    DisplayString 
	  MAX-ACCESS  read-only
	  STATUS   current
	  DESCRIPTION 
	   ""
	  ::= {sensorlistInfoEntry 242}
	sensorName242 OBJECT-TYPE
	  SYNTAX    DisplayString 
	  MAX-ACCESS  read-only
	  STATUS   current
	  DESCRIPTION 
	   ""
	  ::= {sensorlistInfoEntry 243}
	sensorName243 OBJECT-TYPE
	  SYNTAX    DisplayString 
	  MAX-ACCESS  read-only
	  STATUS   current
	  DESCRIPTION 
	   ""
	  ::= {sensorlistInfoEntry 244}
	sensorName244 OBJECT-TYPE
	  SYNTAX    DisplayString 
	  MAX-ACCESS  read-only
	  STATUS   current
	  DESCRIPTION 
	   ""
	  ::= {sensorlistInfoEntry 245}
	sensorName245 OBJECT-TYPE
	  SYNTAX    DisplayString 
	  MAX-ACCESS  read-only
	  STATUS   current
	  DESCRIPTION 
	   ""
	  ::= {sensorlistInfoEntry 246}
	sensorName246 OBJECT-TYPE
	  SYNTAX    DisplayString 
	  MAX-ACCESS  read-only
	  STATUS   current
	  DESCRIPTION 
	   ""
	  ::= {sensorlistInfoEntry 247}
	sensorName247 OBJECT-TYPE
	  SYNTAX    DisplayString 
	  MAX-ACCESS  read-only
	  STATUS   current
	  DESCRIPTION 
	   ""
	  ::= {sensorlistInfoEntry 248}
	sensorName248 OBJECT-TYPE
	  SYNTAX    DisplayString 
	  MAX-ACCESS  read-only
	  STATUS   current
	  DESCRIPTION 
	   ""
	  ::= {sensorlistInfoEntry 249}
	sensorName249 OBJECT-TYPE
	  SYNTAX    DisplayString 
	  MAX-ACCESS  read-only
	  STATUS   current
	  DESCRIPTION 
	   ""
	  ::= {sensorlistInfoEntry 250}
	  
	 
	sensorName250 OBJECT-TYPE
	  SYNTAX    DisplayString 
	  MAX-ACCESS  read-only
	  STATUS   current
	  DESCRIPTION 
	   ""
	  ::= {sensorlistInfoEntry 251}
	sensorName251 OBJECT-TYPE
	  SYNTAX    DisplayString 
	  MAX-ACCESS  read-only
	  STATUS   current
	  DESCRIPTION 
	   ""
	  ::= {sensorlistInfoEntry 252}
	sensorName252 OBJECT-TYPE
	  SYNTAX    DisplayString 
	  MAX-ACCESS  read-only
	  STATUS   current
	  DESCRIPTION 
	   ""
	  ::= {sensorlistInfoEntry 253}
	sensorName253 OBJECT-TYPE
	  SYNTAX    DisplayString 
	  MAX-ACCESS  read-only
	  STATUS   current
	  DESCRIPTION 
	   ""
	  ::= {sensorlistInfoEntry 254}
	sensorName254 OBJECT-TYPE
	  SYNTAX    DisplayString 
	  MAX-ACCESS  read-only
	  STATUS   current
	  DESCRIPTION 
	   ""
	  ::= {sensorlistInfoEntry 255}
	sensorName255 OBJECT-TYPE
	  SYNTAX    DisplayString 
	  MAX-ACCESS  read-only
	  STATUS   current
	  DESCRIPTION 
	   ""
	  ::= {sensorlistInfoEntry 256}
	sensorName256 OBJECT-TYPE
	  SYNTAX    DisplayString 
	  MAX-ACCESS  read-only
	  STATUS   current
	  DESCRIPTION 
	   ""
	  ::= {sensorlistInfoEntry 257}
	
--sensorlistInfoTable end

--sensorReadingInfoTable start
	sensorReadingInfoTable	OBJECT-TYPE
	    SYNTAX     SEQUENCE OF SensorReadingInfoEntry
	    MAX-ACCESS read-only
	    STATUS     current
	    DESCRIPTION
	           "The table display Sensor Reading"
	 	::= {serverAssetInfo 28}
		
	sensorReadingInfoEntry OBJECT-TYPE
	    SYNTAX     SensorReadingInfoEntry
	    MAX-ACCESS read-only
	    STATUS     current
	    DESCRIPTION
	           "The table display Sensor Reading."
	    INDEX   { 
				  sensorReadingInfoIndex
	            }
	    ::= { sensorReadingInfoTable 1 }
		
	SensorReadingInfoEntry ::= 
	SEQUENCE {
	    sensorReadingInfoIndex     Integer32,
		sensorReading1       DisplayString,
		sensorReading2       DisplayString,
		sensorReading3       DisplayString,
		sensorReading4       DisplayString,
		sensorReading5       DisplayString,
		sensorReading6       DisplayString,
		sensorReading7       DisplayString,
		sensorReading8       DisplayString,
		sensorReading9       DisplayString,
		sensorReading10       DisplayString,
		sensorReading11       DisplayString,
		sensorReading12       DisplayString,
		sensorReading13       DisplayString,
		sensorReading14       DisplayString,
		sensorReading15       DisplayString,
		sensorReading16       DisplayString,
		sensorReading17       DisplayString,
		sensorReading18       DisplayString,
		sensorReading19       DisplayString,
		sensorReading20       DisplayString,
		sensorReading21       DisplayString,
		sensorReading22       DisplayString,
		sensorReading23       DisplayString,
		sensorReading24       DisplayString,
		sensorReading25       DisplayString,
		sensorReading26       DisplayString,
		sensorReading27       DisplayString,
		sensorReading28       DisplayString,
		sensorReading29       DisplayString,
		sensorReading30       DisplayString,
		sensorReading31       DisplayString,
		sensorReading32       DisplayString,
		sensorReading33       DisplayString,
		sensorReading34       DisplayString,
		sensorReading35       DisplayString,
		sensorReading36       DisplayString,
		sensorReading37       DisplayString,
		sensorReading38       DisplayString,
		sensorReading39       DisplayString,
		sensorReading40       DisplayString,
		sensorReading41       DisplayString,
		sensorReading42       DisplayString,
		sensorReading43       DisplayString,
		sensorReading44       DisplayString,
		sensorReading45       DisplayString,
		sensorReading46       DisplayString,
		sensorReading47       DisplayString,
		sensorReading48       DisplayString,
		sensorReading49       DisplayString,
		sensorReading50       DisplayString,
		sensorReading51       DisplayString,
		sensorReading52       DisplayString,
		sensorReading53       DisplayString,
		sensorReading54       DisplayString,
		sensorReading55       DisplayString,
		sensorReading56       DisplayString,
		sensorReading57       DisplayString,
		sensorReading58       DisplayString,
		sensorReading59       DisplayString,
		sensorReading60       DisplayString,
		sensorReading61       DisplayString,
		sensorReading62       DisplayString,
		sensorReading63       DisplayString,
		sensorReading64       DisplayString,
		sensorReading65       DisplayString,
		sensorReading66       DisplayString,
		sensorReading67       DisplayString,
		sensorReading68       DisplayString,
		sensorReading69       DisplayString,
		sensorReading70       DisplayString,
		sensorReading71       DisplayString,
		sensorReading72       DisplayString,
		sensorReading73       DisplayString,
		sensorReading74       DisplayString,
		sensorReading75       DisplayString,
		sensorReading76       DisplayString,
		sensorReading77       DisplayString,
		sensorReading78       DisplayString,
		sensorReading79       DisplayString,
		sensorReading80       DisplayString,
		sensorReading81       DisplayString,
		sensorReading82       DisplayString,
		sensorReading83       DisplayString,
		sensorReading84       DisplayString,
		sensorReading85       DisplayString,
		sensorReading86       DisplayString,
		sensorReading87       DisplayString,
		sensorReading88       DisplayString,
		sensorReading89       DisplayString,
		sensorReading90       DisplayString,
		sensorReading91       DisplayString,
		sensorReading92       DisplayString,
		sensorReading93       DisplayString,
		sensorReading94       DisplayString,
		sensorReading95       DisplayString,
		sensorReading96       DisplayString,
		sensorReading97       DisplayString,
		sensorReading98       DisplayString,
		sensorReading99       DisplayString,
		sensorReading100       DisplayString,
		sensorReading101       DisplayString,
		sensorReading102       DisplayString,
		sensorReading103       DisplayString,
		sensorReading104       DisplayString,
		sensorReading105       DisplayString,
		sensorReading106       DisplayString,
		sensorReading107       DisplayString,
		sensorReading108       DisplayString,
		sensorReading109       DisplayString,
		sensorReading110       DisplayString,
		sensorReading111       DisplayString,
		sensorReading112       DisplayString,
		sensorReading113       DisplayString,
		sensorReading114       DisplayString,
		sensorReading115       DisplayString,
		sensorReading116       DisplayString,
		sensorReading117       DisplayString,
		sensorReading118       DisplayString,
		sensorReading119       DisplayString,
		sensorReading120       DisplayString,
		sensorReading121       DisplayString,
		sensorReading122       DisplayString,
		sensorReading123       DisplayString,
		sensorReading124       DisplayString,
		sensorReading125       DisplayString,
		sensorReading126       DisplayString,
		sensorReading127       DisplayString,
		sensorReading128       DisplayString,
		sensorReading129       DisplayString,
		sensorReading130       DisplayString,
		sensorReading131       DisplayString,
		sensorReading132       DisplayString,
		sensorReading133       DisplayString,
		sensorReading134       DisplayString,
		sensorReading135       DisplayString,
		sensorReading136       DisplayString,
		sensorReading137       DisplayString,
		sensorReading138       DisplayString,
		sensorReading139       DisplayString,
		sensorReading140       DisplayString,
		sensorReading141       DisplayString,
		sensorReading142       DisplayString,
		sensorReading143       DisplayString,
		sensorReading144       DisplayString,
		sensorReading145       DisplayString,
		sensorReading146       DisplayString,
		sensorReading147       DisplayString,
		sensorReading148       DisplayString,
		sensorReading149       DisplayString,
		sensorReading150       DisplayString,
		sensorReading151       DisplayString,
		sensorReading152       DisplayString,
		sensorReading153       DisplayString,
		sensorReading154       DisplayString,
		sensorReading155       DisplayString,
		sensorReading156       DisplayString,
		sensorReading157       DisplayString,
		sensorReading158       DisplayString,
		sensorReading159       DisplayString,
		sensorReading160       DisplayString,
		sensorReading161       DisplayString,
		sensorReading162       DisplayString,
		sensorReading163       DisplayString,
		sensorReading164       DisplayString,
		sensorReading165       DisplayString,
		sensorReading166       DisplayString,
		sensorReading167       DisplayString,
		sensorReading168       DisplayString,
		sensorReading169       DisplayString,
		sensorReading170       DisplayString,
		sensorReading171       DisplayString,
		sensorReading172       DisplayString,
		sensorReading173       DisplayString,
		sensorReading174       DisplayString,
		sensorReading175       DisplayString,
		sensorReading176       DisplayString,
		sensorReading177       DisplayString,
		sensorReading178       DisplayString,
		sensorReading179       DisplayString,
		sensorReading180       DisplayString,
		sensorReading181       DisplayString,
		sensorReading182       DisplayString,
		sensorReading183       DisplayString,
		sensorReading184       DisplayString,
		sensorReading185       DisplayString,
		sensorReading186       DisplayString,
		sensorReading187       DisplayString,
		sensorReading188       DisplayString,
		sensorReading189       DisplayString,
		sensorReading190       DisplayString,
		sensorReading191       DisplayString,
		sensorReading192       DisplayString,
		sensorReading193       DisplayString,
		sensorReading194       DisplayString,
		sensorReading195       DisplayString,
		sensorReading196       DisplayString,
		sensorReading197       DisplayString,
		sensorReading198       DisplayString,
		sensorReading199       DisplayString,
		sensorReading200       DisplayString,
		sensorReading201	   DisplayString,
		sensorReading202	   DisplayString,
		sensorReading203	   DisplayString,
		sensorReading204	   DisplayString,
		sensorReading205	   DisplayString,
		sensorReading206	   DisplayString,
		sensorReading207	   DisplayString,
		sensorReading208	   DisplayString,
		sensorReading209	   DisplayString,
		sensorReading210	   DisplayString,
		sensorReading211	   DisplayString,
		sensorReading212	   DisplayString,
		sensorReading213	   DisplayString,
		sensorReading214	   DisplayString,
		sensorReading215	   DisplayString,
		sensorReading216	   DisplayString,
		sensorReading217	   DisplayString,
		sensorReading218	   DisplayString,
		sensorReading219	   DisplayString,
		sensorReading220	   DisplayString,
		sensorReading221	   DisplayString,
		sensorReading222	   DisplayString,
		sensorReading223	   DisplayString,
		sensorReading224	   DisplayString,
		sensorReading225       DisplayString,
		sensorReading226       DisplayString,
		sensorReading227       DisplayString,
		sensorReading228       DisplayString,
		sensorReading229       DisplayString,
		sensorReading230       DisplayString,
		sensorReading231       DisplayString,
		sensorReading232       DisplayString,
		sensorReading233       DisplayString,
		sensorReading234       DisplayString,
		sensorReading235       DisplayString,
		sensorReading236       DisplayString,
		sensorReading237       DisplayString,
		sensorReading238       DisplayString,
		sensorReading239       DisplayString,
		sensorReading240       DisplayString,
		sensorReading241       DisplayString,
		sensorReading242       DisplayString,
		sensorReading243       DisplayString,
		sensorReading244       DisplayString,
		sensorReading245       DisplayString,
		sensorReading246       DisplayString,
		sensorReading247       DisplayString,
		sensorReading248       DisplayString,
		sensorReading249       DisplayString,
		sensorReading250       DisplayString,
		sensorReading251       DisplayString,
		sensorReading252       DisplayString,
		sensorReading253       DisplayString,
		sensorReading254       DisplayString,
		sensorReading255       DisplayString,
		sensorReading256       DisplayString
		
	}
	sensorReadingInfoIndex  OBJECT-TYPE
		SYNTAX 			Integer32
		MAX-ACCESS		read-only
		STATUS			current
		DESCRIPTION 
		"  
			The index value which uniquely identifies 
			the interface to which this entry is applicable.
		"
		::= {sensorReadingInfoEntry 1}           
	         
	sensorReading1 OBJECT-TYPE
		SYNTAX 			DisplayString 
		MAX-ACCESS		read-only
		STATUS			current
		DESCRIPTION 
			""
		::= {sensorReadingInfoEntry 2} 
		
	sensorReading2	OBJECT-TYPE
	  SYNTAX    DisplayString 
	  MAX-ACCESS  read-only
	  STATUS   current
	  DESCRIPTION 
	   ""
	  ::= {sensorReadingInfoEntry 3}
	sensorReading3 OBJECT-TYPE
	  SYNTAX    DisplayString 
	  MAX-ACCESS  read-only
	  STATUS   current
	  DESCRIPTION 
	   ""
	  ::= {sensorReadingInfoEntry 4}
	sensorReading4 OBJECT-TYPE
	  SYNTAX    DisplayString 
	  MAX-ACCESS  read-only
	  STATUS   current
	  DESCRIPTION 
	   ""
	  ::= {sensorReadingInfoEntry 5}
	sensorReading5 OBJECT-TYPE
	  SYNTAX    DisplayString 
	  MAX-ACCESS  read-only
	  STATUS   current
	  DESCRIPTION 
	   ""
	  ::= {sensorReadingInfoEntry 6}
	sensorReading6 OBJECT-TYPE
	  SYNTAX    DisplayString 
	  MAX-ACCESS  read-only
	  STATUS   current
	  DESCRIPTION 
	   ""
	  ::= {sensorReadingInfoEntry 7}
	sensorReading7 OBJECT-TYPE
	  SYNTAX    DisplayString 
	  MAX-ACCESS  read-only
	  STATUS   current
	  DESCRIPTION 
	   ""
	  ::= {sensorReadingInfoEntry 8}
	sensorReading8 OBJECT-TYPE
	  SYNTAX    DisplayString 
	  MAX-ACCESS  read-only
	  STATUS   current
	  DESCRIPTION 
	   ""
	  ::= {sensorReadingInfoEntry 9}
	sensorReading9 OBJECT-TYPE
	  SYNTAX    DisplayString 
	  MAX-ACCESS  read-only
	  STATUS   current
	  DESCRIPTION 
	   ""
	  ::= {sensorReadingInfoEntry 10}
	sensorReading10 OBJECT-TYPE
	  SYNTAX    DisplayString 
	  MAX-ACCESS  read-only
	  STATUS   current
	  DESCRIPTION 
	   ""
	  ::= {sensorReadingInfoEntry 11}
	sensorReading11 OBJECT-TYPE
	  SYNTAX    DisplayString 
	  MAX-ACCESS  read-only
	  STATUS   current
	  DESCRIPTION 
	   ""
	  ::= {sensorReadingInfoEntry 12}
	sensorReading12 OBJECT-TYPE
	  SYNTAX    DisplayString 
	  MAX-ACCESS  read-only
	  STATUS   current
	  DESCRIPTION 
	   ""
	  ::= {sensorReadingInfoEntry 13}
	sensorReading13 OBJECT-TYPE
	  SYNTAX    DisplayString 
	  MAX-ACCESS  read-only
	  STATUS   current
	  DESCRIPTION 
	   ""
	  ::= {sensorReadingInfoEntry 14}
	sensorReading14 OBJECT-TYPE
	  SYNTAX    DisplayString 
	  MAX-ACCESS  read-only
	  STATUS   current
	  DESCRIPTION 
	   ""
	  ::= {sensorReadingInfoEntry 15}
	sensorReading15 OBJECT-TYPE
	  SYNTAX    DisplayString 
	  MAX-ACCESS  read-only
	  STATUS   current
	  DESCRIPTION 
	   ""
	  ::= {sensorReadingInfoEntry 16}
	sensorReading16 OBJECT-TYPE
	  SYNTAX    DisplayString 
	  MAX-ACCESS  read-only
	  STATUS   current
	  DESCRIPTION 
	   ""
	  ::= {sensorReadingInfoEntry 17}
	sensorReading17 OBJECT-TYPE
	  SYNTAX    DisplayString 
	  MAX-ACCESS  read-only
	  STATUS   current
	  DESCRIPTION 
	   ""
	  ::= {sensorReadingInfoEntry 18}
	sensorReading18 OBJECT-TYPE
	  SYNTAX    DisplayString 
	  MAX-ACCESS  read-only
	  STATUS   current
	  DESCRIPTION 
	   ""
	  ::= {sensorReadingInfoEntry 19}
	sensorReading19 OBJECT-TYPE
	  SYNTAX    DisplayString 
	  MAX-ACCESS  read-only
	  STATUS   current
	  DESCRIPTION 
	   ""
	  ::= {sensorReadingInfoEntry 20}
	  
	sensorReading20 OBJECT-TYPE
	  SYNTAX    DisplayString 
	  MAX-ACCESS  read-only
	  STATUS   current
	  DESCRIPTION 
	   ""
	  ::= {sensorReadingInfoEntry 21}
	sensorReading21 OBJECT-TYPE
	  SYNTAX    DisplayString 
	  MAX-ACCESS  read-only
	  STATUS   current
	  DESCRIPTION 
	   ""
	  ::= {sensorReadingInfoEntry 22}
	sensorReading22 OBJECT-TYPE
	  SYNTAX    DisplayString 
	  MAX-ACCESS  read-only
	  STATUS   current
	  DESCRIPTION 
	   ""
	  ::= {sensorReadingInfoEntry 23}
	sensorReading23 OBJECT-TYPE
	  SYNTAX    DisplayString 
	  MAX-ACCESS  read-only
	  STATUS   current
	  DESCRIPTION 
	   ""
	  ::= {sensorReadingInfoEntry 24}
	sensorReading24 OBJECT-TYPE
	  SYNTAX    DisplayString 
	  MAX-ACCESS  read-only
	  STATUS   current
	  DESCRIPTION 
	   ""
	  ::= {sensorReadingInfoEntry 25}
	sensorReading25 OBJECT-TYPE
	  SYNTAX    DisplayString 
	  MAX-ACCESS  read-only
	  STATUS   current
	  DESCRIPTION 
	   ""
	  ::= {sensorReadingInfoEntry 26}
	sensorReading26 OBJECT-TYPE
	  SYNTAX    DisplayString 
	  MAX-ACCESS  read-only
	  STATUS   current
	  DESCRIPTION 
	   ""
	  ::= {sensorReadingInfoEntry 27}
	sensorReading27 OBJECT-TYPE
	  SYNTAX    DisplayString 
	  MAX-ACCESS  read-only
	  STATUS   current
	  DESCRIPTION 
	   ""
	  ::= {sensorReadingInfoEntry 28}
	sensorReading28 OBJECT-TYPE
	  SYNTAX    DisplayString 
	  MAX-ACCESS  read-only
	  STATUS   current
	  DESCRIPTION 
	   ""
	  ::= {sensorReadingInfoEntry 29}
	sensorReading29 OBJECT-TYPE
	  SYNTAX    DisplayString 
	  MAX-ACCESS  read-only
	  STATUS   current
	  DESCRIPTION 
	   ""
	  ::= {sensorReadingInfoEntry 30}
	 
	  
	sensorReading30 OBJECT-TYPE
	  SYNTAX    DisplayString 
	  MAX-ACCESS  read-only
	  STATUS   current
	  DESCRIPTION 
	   ""
	  ::= {sensorReadingInfoEntry 31}
	sensorReading31 OBJECT-TYPE
	  SYNTAX    DisplayString 
	  MAX-ACCESS  read-only
	  STATUS   current
	  DESCRIPTION 
	   ""
	  ::= {sensorReadingInfoEntry 32}
	sensorReading32 OBJECT-TYPE
	  SYNTAX    DisplayString 
	  MAX-ACCESS  read-only
	  STATUS   current
	  DESCRIPTION 
	   ""
	  ::= {sensorReadingInfoEntry 33}
	sensorReading33 OBJECT-TYPE
	  SYNTAX    DisplayString 
	  MAX-ACCESS  read-only
	  STATUS   current
	  DESCRIPTION 
	   ""
	  ::= {sensorReadingInfoEntry 34}
	sensorReading34 OBJECT-TYPE
	  SYNTAX    DisplayString 
	  MAX-ACCESS  read-only
	  STATUS   current
	  DESCRIPTION 
	   ""
	  ::= {sensorReadingInfoEntry 35}
	sensorReading35 OBJECT-TYPE
	  SYNTAX    DisplayString 
	  MAX-ACCESS  read-only
	  STATUS   current
	  DESCRIPTION 
	   ""
	  ::= {sensorReadingInfoEntry 36}
	sensorReading36 OBJECT-TYPE
	  SYNTAX    DisplayString 
	  MAX-ACCESS  read-only
	  STATUS   current
	  DESCRIPTION 
	   ""
	  ::= {sensorReadingInfoEntry 37}
	sensorReading37 OBJECT-TYPE
	  SYNTAX    DisplayString 
	  MAX-ACCESS  read-only
	  STATUS   current
	  DESCRIPTION 
	   ""
	  ::= {sensorReadingInfoEntry 38}
	sensorReading38 OBJECT-TYPE
	  SYNTAX    DisplayString 
	  MAX-ACCESS  read-only
	  STATUS   current
	  DESCRIPTION 
	   ""
	  ::= {sensorReadingInfoEntry 39}
	sensorReading39 OBJECT-TYPE
	  SYNTAX    DisplayString 
	  MAX-ACCESS  read-only
	  STATUS   current
	  DESCRIPTION 
	   ""
	  ::= {sensorReadingInfoEntry 40}


	sensorReading40 OBJECT-TYPE
	  SYNTAX    DisplayString 
	  MAX-ACCESS  read-only
	  STATUS   current
	  DESCRIPTION 
	   ""
	  ::= {sensorReadingInfoEntry 41}
	sensorReading41 OBJECT-TYPE
	  SYNTAX    DisplayString 
	  MAX-ACCESS  read-only
	  STATUS   current
	  DESCRIPTION 
	   ""
	  ::= {sensorReadingInfoEntry 42}
	sensorReading42 OBJECT-TYPE
	  SYNTAX    DisplayString 
	  MAX-ACCESS  read-only
	  STATUS   current
	  DESCRIPTION 
	   ""
	  ::= {sensorReadingInfoEntry 43}
	sensorReading43 OBJECT-TYPE
	  SYNTAX    DisplayString 
	  MAX-ACCESS  read-only
	  STATUS   current
	  DESCRIPTION 
	   ""
	  ::= {sensorReadingInfoEntry 44}
	sensorReading44 OBJECT-TYPE
	  SYNTAX    DisplayString 
	  MAX-ACCESS  read-only
	  STATUS   current
	  DESCRIPTION 
	   ""
	  ::= {sensorReadingInfoEntry 45}
	sensorReading45 OBJECT-TYPE
	  SYNTAX    DisplayString 
	  MAX-ACCESS  read-only
	  STATUS   current
	  DESCRIPTION 
	   ""
	  ::= {sensorReadingInfoEntry 46}
	sensorReading46 OBJECT-TYPE
	  SYNTAX    DisplayString 
	  MAX-ACCESS  read-only
	  STATUS   current
	  DESCRIPTION 
	   ""
	  ::= {sensorReadingInfoEntry 47}
	sensorReading47 OBJECT-TYPE
	  SYNTAX    DisplayString 
	  MAX-ACCESS  read-only
	  STATUS   current
	  DESCRIPTION 
	   ""
	  ::= {sensorReadingInfoEntry 48}
	sensorReading48 OBJECT-TYPE
	  SYNTAX    DisplayString 
	  MAX-ACCESS  read-only
	  STATUS   current
	  DESCRIPTION 
	   ""
	  ::= {sensorReadingInfoEntry 49}
	sensorReading49 OBJECT-TYPE
	  SYNTAX    DisplayString 
	  MAX-ACCESS  read-only
	  STATUS   current
	  DESCRIPTION 
	   ""
	  ::= {sensorReadingInfoEntry 50}
	  
	  
	sensorReading50 OBJECT-TYPE
	  SYNTAX    DisplayString 
	  MAX-ACCESS  read-only
	  STATUS   current
	  DESCRIPTION 
	   ""
	  ::= {sensorReadingInfoEntry 51}
	sensorReading51 OBJECT-TYPE
	  SYNTAX    DisplayString 
	  MAX-ACCESS  read-only
	  STATUS   current
	  DESCRIPTION 
	   ""
	  ::= {sensorReadingInfoEntry 52}
	sensorReading52 OBJECT-TYPE
	  SYNTAX    DisplayString 
	  MAX-ACCESS  read-only
	  STATUS   current
	  DESCRIPTION 
	   ""
	  ::= {sensorReadingInfoEntry 53}
	sensorReading53 OBJECT-TYPE
	  SYNTAX    DisplayString 
	  MAX-ACCESS  read-only
	  STATUS   current
	  DESCRIPTION 
	   ""
	  ::= {sensorReadingInfoEntry 54}
	sensorReading54 OBJECT-TYPE
	  SYNTAX    DisplayString 
	  MAX-ACCESS  read-only
	  STATUS   current
	  DESCRIPTION 
	   ""
	  ::= {sensorReadingInfoEntry 55}
	sensorReading55 OBJECT-TYPE
	  SYNTAX    DisplayString 
	  MAX-ACCESS  read-only
	  STATUS   current
	  DESCRIPTION 
	   ""
	  ::= {sensorReadingInfoEntry 56}
	sensorReading56 OBJECT-TYPE
	  SYNTAX    DisplayString 
	  MAX-ACCESS  read-only
	  STATUS   current
	  DESCRIPTION 
	   ""
	  ::= {sensorReadingInfoEntry 57}
	sensorReading57 OBJECT-TYPE
	  SYNTAX    DisplayString 
	  MAX-ACCESS  read-only
	  STATUS   current
	  DESCRIPTION 
	   ""
	  ::= {sensorReadingInfoEntry 58}
	sensorReading58 OBJECT-TYPE
	  SYNTAX    DisplayString 
	  MAX-ACCESS  read-only
	  STATUS   current
	  DESCRIPTION 
	   ""
	  ::= {sensorReadingInfoEntry 59}
	sensorReading59 OBJECT-TYPE
	  SYNTAX    DisplayString 
	  MAX-ACCESS  read-only
	  STATUS   current
	  DESCRIPTION 
	   ""
	  ::= {sensorReadingInfoEntry 60}
	  
	  
	sensorReading60 OBJECT-TYPE
	  SYNTAX    DisplayString 
	  MAX-ACCESS  read-only
	  STATUS   current
	  DESCRIPTION 
	   ""
	  ::= {sensorReadingInfoEntry 61}
	sensorReading61 OBJECT-TYPE
	  SYNTAX    DisplayString 
	  MAX-ACCESS  read-only
	  STATUS   current
	  DESCRIPTION 
	   ""
	  ::= {sensorReadingInfoEntry 62}
	sensorReading62 OBJECT-TYPE
	  SYNTAX    DisplayString 
	  MAX-ACCESS  read-only
	  STATUS   current
	  DESCRIPTION 
	   ""
	  ::= {sensorReadingInfoEntry 63}
	sensorReading63 OBJECT-TYPE
	  SYNTAX    DisplayString 
	  MAX-ACCESS  read-only
	  STATUS   current
	  DESCRIPTION 
	   ""
	  ::= {sensorReadingInfoEntry 64}
	sensorReading64 OBJECT-TYPE
	  SYNTAX    DisplayString 
	  MAX-ACCESS  read-only
	  STATUS   current
	  DESCRIPTION 
	   ""
	  ::= {sensorReadingInfoEntry 65}
	sensorReading65 OBJECT-TYPE
	  SYNTAX    DisplayString 
	  MAX-ACCESS  read-only
	  STATUS   current
	  DESCRIPTION 
	   ""
	  ::= {sensorReadingInfoEntry 66}
	sensorReading66 OBJECT-TYPE
	  SYNTAX    DisplayString 
	  MAX-ACCESS  read-only
	  STATUS   current
	  DESCRIPTION 
	   ""
	  ::= {sensorReadingInfoEntry 67}
	sensorReading67 OBJECT-TYPE
	  SYNTAX    DisplayString 
	  MAX-ACCESS  read-only
	  STATUS   current
	  DESCRIPTION 
	   ""
	  ::= {sensorReadingInfoEntry 68}
	sensorReading68 OBJECT-TYPE
	  SYNTAX    DisplayString 
	  MAX-ACCESS  read-only
	  STATUS   current
	  DESCRIPTION 
	   ""
	  ::= {sensorReadingInfoEntry 69}
	sensorReading69 OBJECT-TYPE
	  SYNTAX    DisplayString 
	  MAX-ACCESS  read-only
	  STATUS   current
	  DESCRIPTION 
	   ""
	  ::= {sensorReadingInfoEntry 70}
	  
	 
	sensorReading70 OBJECT-TYPE
	  SYNTAX    DisplayString 
	  MAX-ACCESS  read-only
	  STATUS   current
	  DESCRIPTION 
	   ""
	  ::= {sensorReadingInfoEntry 71}
	sensorReading71 OBJECT-TYPE
	  SYNTAX    DisplayString 
	  MAX-ACCESS  read-only
	  STATUS   current
	  DESCRIPTION 
	   ""
	  ::= {sensorReadingInfoEntry 72}
	sensorReading72 OBJECT-TYPE
	  SYNTAX    DisplayString 
	  MAX-ACCESS  read-only
	  STATUS   current
	  DESCRIPTION 
	   ""
	  ::= {sensorReadingInfoEntry 73}
	sensorReading73 OBJECT-TYPE
	  SYNTAX    DisplayString 
	  MAX-ACCESS  read-only
	  STATUS   current
	  DESCRIPTION 
	   ""
	  ::= {sensorReadingInfoEntry 74}
	sensorReading74 OBJECT-TYPE
	  SYNTAX    DisplayString 
	  MAX-ACCESS  read-only
	  STATUS   current
	  DESCRIPTION 
	   ""
	  ::= {sensorReadingInfoEntry 75}
	sensorReading75 OBJECT-TYPE
	  SYNTAX    DisplayString 
	  MAX-ACCESS  read-only
	  STATUS   current
	  DESCRIPTION 
	   ""
	  ::= {sensorReadingInfoEntry 76}
	sensorReading76 OBJECT-TYPE
	  SYNTAX    DisplayString 
	  MAX-ACCESS  read-only
	  STATUS   current
	  DESCRIPTION 
	   ""
	  ::= {sensorReadingInfoEntry 77}
	sensorReading77 OBJECT-TYPE
	  SYNTAX    DisplayString 
	  MAX-ACCESS  read-only
	  STATUS   current
	  DESCRIPTION 
	   ""
	  ::= {sensorReadingInfoEntry 78}
	sensorReading78 OBJECT-TYPE
	  SYNTAX    DisplayString 
	  MAX-ACCESS  read-only
	  STATUS   current
	  DESCRIPTION 
	   ""
	  ::= {sensorReadingInfoEntry 79}
	sensorReading79 OBJECT-TYPE
	  SYNTAX    DisplayString 
	  MAX-ACCESS  read-only
	  STATUS   current
	  DESCRIPTION 
	   ""
	  ::= {sensorReadingInfoEntry 80}
	  
	 
	sensorReading80 OBJECT-TYPE
	  SYNTAX    DisplayString 
	  MAX-ACCESS  read-only
	  STATUS   current
	  DESCRIPTION 
	   ""
	  ::= {sensorReadingInfoEntry 81}
	sensorReading81 OBJECT-TYPE
	  SYNTAX    DisplayString 
	  MAX-ACCESS  read-only
	  STATUS   current
	  DESCRIPTION 
	   ""
	  ::= {sensorReadingInfoEntry 82}
	sensorReading82 OBJECT-TYPE
	  SYNTAX    DisplayString 
	  MAX-ACCESS  read-only
	  STATUS   current
	  DESCRIPTION 
	   ""
	  ::= {sensorReadingInfoEntry 83}
	sensorReading83 OBJECT-TYPE
	  SYNTAX    DisplayString 
	  MAX-ACCESS  read-only
	  STATUS   current
	  DESCRIPTION 
	   ""
	  ::= {sensorReadingInfoEntry 84}
	sensorReading84 OBJECT-TYPE
	  SYNTAX    DisplayString 
	  MAX-ACCESS  read-only
	  STATUS   current
	  DESCRIPTION 
	   ""
	  ::= {sensorReadingInfoEntry 85}
	sensorReading85 OBJECT-TYPE
	  SYNTAX    DisplayString 
	  MAX-ACCESS  read-only
	  STATUS   current
	  DESCRIPTION 
	   ""
	  ::= {sensorReadingInfoEntry 86}
	sensorReading86 OBJECT-TYPE
	  SYNTAX    DisplayString 
	  MAX-ACCESS  read-only
	  STATUS   current
	  DESCRIPTION 
	   ""
	  ::= {sensorReadingInfoEntry 87}
	sensorReading87 OBJECT-TYPE
	  SYNTAX    DisplayString 
	  MAX-ACCESS  read-only
	  STATUS   current
	  DESCRIPTION 
	   ""
	  ::= {sensorReadingInfoEntry 88}
	sensorReading88 OBJECT-TYPE
	  SYNTAX    DisplayString 
	  MAX-ACCESS  read-only
	  STATUS   current
	  DESCRIPTION 
	   ""
	  ::= {sensorReadingInfoEntry 89}
	sensorReading89 OBJECT-TYPE
	  SYNTAX    DisplayString 
	  MAX-ACCESS  read-only
	  STATUS   current
	  DESCRIPTION 
	   ""
	  ::= {sensorReadingInfoEntry 90}
	  
	 
	sensorReading90 OBJECT-TYPE
	  SYNTAX    DisplayString 
	  MAX-ACCESS  read-only
	  STATUS   current
	  DESCRIPTION 
	   ""
	  ::= {sensorReadingInfoEntry 91}
	sensorReading91 OBJECT-TYPE
	  SYNTAX    DisplayString 
	  MAX-ACCESS  read-only
	  STATUS   current
	  DESCRIPTION 
	   ""
	  ::= {sensorReadingInfoEntry 92}
	sensorReading92 OBJECT-TYPE
	  SYNTAX    DisplayString 
	  MAX-ACCESS  read-only
	  STATUS   current
	  DESCRIPTION 
	   ""
	  ::= {sensorReadingInfoEntry 93}
	sensorReading93 OBJECT-TYPE
	  SYNTAX    DisplayString 
	  MAX-ACCESS  read-only
	  STATUS   current
	  DESCRIPTION 
	   ""
	  ::= {sensorReadingInfoEntry 94}
	sensorReading94 OBJECT-TYPE
	  SYNTAX    DisplayString 
	  MAX-ACCESS  read-only
	  STATUS   current
	  DESCRIPTION 
	   ""
	  ::= {sensorReadingInfoEntry 95}
	sensorReading95 OBJECT-TYPE
	  SYNTAX    DisplayString 
	  MAX-ACCESS  read-only
	  STATUS   current
	  DESCRIPTION 
	   ""
	  ::= {sensorReadingInfoEntry 96}
	sensorReading96 OBJECT-TYPE
	  SYNTAX    DisplayString 
	  MAX-ACCESS  read-only
	  STATUS   current
	  DESCRIPTION 
	   ""
	  ::= {sensorReadingInfoEntry 97}
	sensorReading97 OBJECT-TYPE
	  SYNTAX    DisplayString 
	  MAX-ACCESS  read-only
	  STATUS   current
	  DESCRIPTION 
	   ""
	  ::= {sensorReadingInfoEntry 98}
	sensorReading98 OBJECT-TYPE
	  SYNTAX    DisplayString 
	  MAX-ACCESS  read-only
	  STATUS   current
	  DESCRIPTION 
	   ""
	  ::= {sensorReadingInfoEntry 99}
	sensorReading99 OBJECT-TYPE
	  SYNTAX    DisplayString 
	  MAX-ACCESS  read-only
	  STATUS   current
	  DESCRIPTION 
	   ""
	  ::= {sensorReadingInfoEntry 100}
	  
	 
	sensorReading100 OBJECT-TYPE
	  SYNTAX    DisplayString 
	  MAX-ACCESS  read-only
	  STATUS   current
	  DESCRIPTION 
	   ""
	  ::= {sensorReadingInfoEntry 101}
	sensorReading101 OBJECT-TYPE
	  SYNTAX    DisplayString 
	  MAX-ACCESS  read-only
	  STATUS   current
	  DESCRIPTION 
	   ""
	  ::= {sensorReadingInfoEntry 102}
	sensorReading102 OBJECT-TYPE
	  SYNTAX    DisplayString 
	  MAX-ACCESS  read-only
	  STATUS   current
	  DESCRIPTION 
	   ""
	  ::= {sensorReadingInfoEntry 103}
	sensorReading103 OBJECT-TYPE
	  SYNTAX    DisplayString 
	  MAX-ACCESS  read-only
	  STATUS   current
	  DESCRIPTION 
	   ""
	  ::= {sensorReadingInfoEntry 104}
	sensorReading104 OBJECT-TYPE
	  SYNTAX    DisplayString 
	  MAX-ACCESS  read-only
	  STATUS   current
	  DESCRIPTION 
	   ""
	  ::= {sensorReadingInfoEntry 105}
	sensorReading105 OBJECT-TYPE
	  SYNTAX    DisplayString 
	  MAX-ACCESS  read-only
	  STATUS   current
	  DESCRIPTION 
	   ""
	  ::= {sensorReadingInfoEntry 106}
	sensorReading106 OBJECT-TYPE
	  SYNTAX    DisplayString 
	  MAX-ACCESS  read-only
	  STATUS   current
	  DESCRIPTION 
	   ""
	  ::= {sensorReadingInfoEntry 107}
	sensorReading107 OBJECT-TYPE
	  SYNTAX    DisplayString 
	  MAX-ACCESS  read-only
	  STATUS   current
	  DESCRIPTION 
	   ""
	  ::= {sensorReadingInfoEntry 108}
	sensorReading108 OBJECT-TYPE
	  SYNTAX    DisplayString 
	  MAX-ACCESS  read-only
	  STATUS   current
	  DESCRIPTION 
	   ""
	  ::= {sensorReadingInfoEntry 109}
	sensorReading109 OBJECT-TYPE
	  SYNTAX    DisplayString 
	  MAX-ACCESS  read-only
	  STATUS   current
	  DESCRIPTION 
	   ""
	  ::= {sensorReadingInfoEntry 110}
	  
	 
	sensorReading110 OBJECT-TYPE
	  SYNTAX    DisplayString 
	  MAX-ACCESS  read-only
	  STATUS   current
	  DESCRIPTION 
	   ""
	  ::= {sensorReadingInfoEntry 111}
	sensorReading111 OBJECT-TYPE
	  SYNTAX    DisplayString 
	  MAX-ACCESS  read-only
	  STATUS   current
	  DESCRIPTION 
	   ""
	  ::= {sensorReadingInfoEntry 112}
	sensorReading112 OBJECT-TYPE
	  SYNTAX    DisplayString 
	  MAX-ACCESS  read-only
	  STATUS   current
	  DESCRIPTION 
	   ""
	  ::= {sensorReadingInfoEntry 113}
	sensorReading113 OBJECT-TYPE
	  SYNTAX    DisplayString 
	  MAX-ACCESS  read-only
	  STATUS   current
	  DESCRIPTION 
	   ""
	  ::= {sensorReadingInfoEntry 114}
	sensorReading114 OBJECT-TYPE
	  SYNTAX    DisplayString 
	  MAX-ACCESS  read-only
	  STATUS   current
	  DESCRIPTION 
	   ""
	  ::= {sensorReadingInfoEntry 115}
	sensorReading115 OBJECT-TYPE
	  SYNTAX    DisplayString 
	  MAX-ACCESS  read-only
	  STATUS   current
	  DESCRIPTION 
	   ""
	  ::= {sensorReadingInfoEntry 116}
	sensorReading116 OBJECT-TYPE
	  SYNTAX    DisplayString 
	  MAX-ACCESS  read-only
	  STATUS   current
	  DESCRIPTION 
	   ""
	  ::= {sensorReadingInfoEntry 117}
	sensorReading117 OBJECT-TYPE
	  SYNTAX    DisplayString 
	  MAX-ACCESS  read-only
	  STATUS   current
	  DESCRIPTION 
	   ""
	  ::= {sensorReadingInfoEntry 118}
	sensorReading118 OBJECT-TYPE
	  SYNTAX    DisplayString 
	  MAX-ACCESS  read-only
	  STATUS   current
	  DESCRIPTION 
	   ""
	  ::= {sensorReadingInfoEntry 119}
	sensorReading119 OBJECT-TYPE
	  SYNTAX    DisplayString 
	  MAX-ACCESS  read-only
	  STATUS   current
	  DESCRIPTION 
	   ""
	  ::= {sensorReadingInfoEntry 120}
	  
	 
	sensorReading120 OBJECT-TYPE
	  SYNTAX    DisplayString 
	  MAX-ACCESS  read-only
	  STATUS   current
	  DESCRIPTION 
	   ""
	  ::= {sensorReadingInfoEntry 121}
	sensorReading121 OBJECT-TYPE
	  SYNTAX    DisplayString 
	  MAX-ACCESS  read-only
	  STATUS   current
	  DESCRIPTION 
	   ""
	  ::= {sensorReadingInfoEntry 122}
	sensorReading122 OBJECT-TYPE
	  SYNTAX    DisplayString 
	  MAX-ACCESS  read-only
	  STATUS   current
	  DESCRIPTION 
	   ""
	  ::= {sensorReadingInfoEntry 123}
	sensorReading123 OBJECT-TYPE
	  SYNTAX    DisplayString 
	  MAX-ACCESS  read-only
	  STATUS   current
	  DESCRIPTION 
	   ""
	  ::= {sensorReadingInfoEntry 124}
	sensorReading124 OBJECT-TYPE
	  SYNTAX    DisplayString 
	  MAX-ACCESS  read-only
	  STATUS   current
	  DESCRIPTION 
	   ""
	  ::= {sensorReadingInfoEntry 125}
	sensorReading125 OBJECT-TYPE
	  SYNTAX    DisplayString 
	  MAX-ACCESS  read-only
	  STATUS   current
	  DESCRIPTION 
	   ""
	  ::= {sensorReadingInfoEntry 126}
	sensorReading126 OBJECT-TYPE
	  SYNTAX    DisplayString 
	  MAX-ACCESS  read-only
	  STATUS   current
	  DESCRIPTION 
	   ""
	  ::= {sensorReadingInfoEntry 127}
	sensorReading127 OBJECT-TYPE
	  SYNTAX    DisplayString 
	  MAX-ACCESS  read-only
	  STATUS   current
	  DESCRIPTION 
	   ""
	  ::= {sensorReadingInfoEntry 128}
	sensorReading128 OBJECT-TYPE
	  SYNTAX    DisplayString 
	  MAX-ACCESS  read-only
	  STATUS   current
	  DESCRIPTION 
	   ""
	  ::= {sensorReadingInfoEntry 129}
	sensorReading129 OBJECT-TYPE
	  SYNTAX    DisplayString 
	  MAX-ACCESS  read-only
	  STATUS   current
	  DESCRIPTION 
	   ""
	  ::= {sensorReadingInfoEntry 130}
	  
	 
	sensorReading130 OBJECT-TYPE
	  SYNTAX    DisplayString 
	  MAX-ACCESS  read-only
	  STATUS   current
	  DESCRIPTION 
	   ""
	  ::= {sensorReadingInfoEntry 131}
	sensorReading131 OBJECT-TYPE
	  SYNTAX    DisplayString 
	  MAX-ACCESS  read-only
	  STATUS   current
	  DESCRIPTION 
	   ""
	  ::= {sensorReadingInfoEntry 132}
	sensorReading132 OBJECT-TYPE
	  SYNTAX    DisplayString 
	  MAX-ACCESS  read-only
	  STATUS   current
	  DESCRIPTION 
	   ""
	  ::= {sensorReadingInfoEntry 133}
	sensorReading133 OBJECT-TYPE
	  SYNTAX    DisplayString 
	  MAX-ACCESS  read-only
	  STATUS   current
	  DESCRIPTION 
	   ""
	  ::= {sensorReadingInfoEntry 134}
	sensorReading134 OBJECT-TYPE
	  SYNTAX    DisplayString 
	  MAX-ACCESS  read-only
	  STATUS   current
	  DESCRIPTION 
	   ""
	  ::= {sensorReadingInfoEntry 135}
	sensorReading135 OBJECT-TYPE
	  SYNTAX    DisplayString 
	  MAX-ACCESS  read-only
	  STATUS   current
	  DESCRIPTION 
	   ""
	  ::= {sensorReadingInfoEntry 136}
	sensorReading136 OBJECT-TYPE
	  SYNTAX    DisplayString 
	  MAX-ACCESS  read-only
	  STATUS   current
	  DESCRIPTION 
	   ""
	  ::= {sensorReadingInfoEntry 137}
	sensorReading137 OBJECT-TYPE
	  SYNTAX    DisplayString 
	  MAX-ACCESS  read-only
	  STATUS   current
	  DESCRIPTION 
	   ""
	  ::= {sensorReadingInfoEntry 138}
	sensorReading138 OBJECT-TYPE
	  SYNTAX    DisplayString 
	  MAX-ACCESS  read-only
	  STATUS   current
	  DESCRIPTION 
	   ""
	  ::= {sensorReadingInfoEntry 139}
	sensorReading139 OBJECT-TYPE
	  SYNTAX    DisplayString 
	  MAX-ACCESS  read-only
	  STATUS   current
	  DESCRIPTION 
	   ""
	  ::= {sensorReadingInfoEntry 140}
	  
	 
	sensorReading140 OBJECT-TYPE
	  SYNTAX    DisplayString 
	  MAX-ACCESS  read-only
	  STATUS   current
	  DESCRIPTION 
	   ""
	  ::= {sensorReadingInfoEntry 141}
	sensorReading141 OBJECT-TYPE
	  SYNTAX    DisplayString 
	  MAX-ACCESS  read-only
	  STATUS   current
	  DESCRIPTION 
	   ""
	  ::= {sensorReadingInfoEntry 142}
	sensorReading142 OBJECT-TYPE
	  SYNTAX    DisplayString 
	  MAX-ACCESS  read-only
	  STATUS   current
	  DESCRIPTION 
	   ""
	  ::= {sensorReadingInfoEntry 143}
	sensorReading143 OBJECT-TYPE
	  SYNTAX    DisplayString 
	  MAX-ACCESS  read-only
	  STATUS   current
	  DESCRIPTION 
	   ""
	  ::= {sensorReadingInfoEntry 144}
	sensorReading144 OBJECT-TYPE
	  SYNTAX    DisplayString 
	  MAX-ACCESS  read-only
	  STATUS   current
	  DESCRIPTION 
	   ""
	  ::= {sensorReadingInfoEntry 145}
	sensorReading145 OBJECT-TYPE
	  SYNTAX    DisplayString 
	  MAX-ACCESS  read-only
	  STATUS   current
	  DESCRIPTION 
	   ""
	  ::= {sensorReadingInfoEntry 146}
	sensorReading146 OBJECT-TYPE
	  SYNTAX    DisplayString 
	  MAX-ACCESS  read-only
	  STATUS   current
	  DESCRIPTION 
	   ""
	  ::= {sensorReadingInfoEntry 147}
	sensorReading147 OBJECT-TYPE
	  SYNTAX    DisplayString 
	  MAX-ACCESS  read-only
	  STATUS   current
	  DESCRIPTION 
	   ""
	  ::= {sensorReadingInfoEntry 148}
	sensorReading148 OBJECT-TYPE
	  SYNTAX    DisplayString 
	  MAX-ACCESS  read-only
	  STATUS   current
	  DESCRIPTION 
	   ""
	  ::= {sensorReadingInfoEntry 149}
	sensorReading149 OBJECT-TYPE
	  SYNTAX    DisplayString 
	  MAX-ACCESS  read-only
	  STATUS   current
	  DESCRIPTION 
	   ""
	  ::= {sensorReadingInfoEntry 150}
	  
	 
	sensorReading150 OBJECT-TYPE
	  SYNTAX    DisplayString 
	  MAX-ACCESS  read-only
	  STATUS   current
	  DESCRIPTION 
	   ""
	  ::= {sensorReadingInfoEntry 151}
	sensorReading151 OBJECT-TYPE
	  SYNTAX    DisplayString 
	  MAX-ACCESS  read-only
	  STATUS   current
	  DESCRIPTION 
	   ""
	  ::= {sensorReadingInfoEntry 152}
	sensorReading152 OBJECT-TYPE
	  SYNTAX    DisplayString 
	  MAX-ACCESS  read-only
	  STATUS   current
	  DESCRIPTION 
	   ""
	  ::= {sensorReadingInfoEntry 153}
	sensorReading153 OBJECT-TYPE
	  SYNTAX    DisplayString 
	  MAX-ACCESS  read-only
	  STATUS   current
	  DESCRIPTION 
	   ""
	  ::= {sensorReadingInfoEntry 154}
	sensorReading154 OBJECT-TYPE
	  SYNTAX    DisplayString 
	  MAX-ACCESS  read-only
	  STATUS   current
	  DESCRIPTION 
	   ""
	  ::= {sensorReadingInfoEntry 155}
	sensorReading155 OBJECT-TYPE
	  SYNTAX    DisplayString 
	  MAX-ACCESS  read-only
	  STATUS   current
	  DESCRIPTION 
	   ""
	  ::= {sensorReadingInfoEntry 156}
	sensorReading156 OBJECT-TYPE
	  SYNTAX    DisplayString 
	  MAX-ACCESS  read-only
	  STATUS   current
	  DESCRIPTION 
	   ""
	  ::= {sensorReadingInfoEntry 157}
	sensorReading157 OBJECT-TYPE
	  SYNTAX    DisplayString 
	  MAX-ACCESS  read-only
	  STATUS   current
	  DESCRIPTION 
	   ""
	  ::= {sensorReadingInfoEntry 158}
	sensorReading158 OBJECT-TYPE
	  SYNTAX    DisplayString 
	  MAX-ACCESS  read-only
	  STATUS   current
	  DESCRIPTION 
	   ""
	  ::= {sensorReadingInfoEntry 159}
	sensorReading159 OBJECT-TYPE
	  SYNTAX    DisplayString 
	  MAX-ACCESS  read-only
	  STATUS   current
	  DESCRIPTION 
	   ""
	  ::= {sensorReadingInfoEntry 160}
	  
	 
	sensorReading160 OBJECT-TYPE
	  SYNTAX    DisplayString 
	  MAX-ACCESS  read-only
	  STATUS   current
	  DESCRIPTION 
	   ""
	  ::= {sensorReadingInfoEntry 161}
	sensorReading161 OBJECT-TYPE
	  SYNTAX    DisplayString 
	  MAX-ACCESS  read-only
	  STATUS   current
	  DESCRIPTION 
	   ""
	  ::= {sensorReadingInfoEntry 162}
	sensorReading162 OBJECT-TYPE
	  SYNTAX    DisplayString 
	  MAX-ACCESS  read-only
	  STATUS   current
	  DESCRIPTION 
	   ""
	  ::= {sensorReadingInfoEntry 163}
	sensorReading163 OBJECT-TYPE
	  SYNTAX    DisplayString 
	  MAX-ACCESS  read-only
	  STATUS   current
	  DESCRIPTION 
	   ""
	  ::= {sensorReadingInfoEntry 164}
	sensorReading164 OBJECT-TYPE
	  SYNTAX    DisplayString 
	  MAX-ACCESS  read-only
	  STATUS   current
	  DESCRIPTION 
	   ""
	  ::= {sensorReadingInfoEntry 165}
	sensorReading165 OBJECT-TYPE
	  SYNTAX    DisplayString 
	  MAX-ACCESS  read-only
	  STATUS   current
	  DESCRIPTION 
	   ""
	  ::= {sensorReadingInfoEntry 166}
	sensorReading166 OBJECT-TYPE
	  SYNTAX    DisplayString 
	  MAX-ACCESS  read-only
	  STATUS   current
	  DESCRIPTION 
	   ""
	  ::= {sensorReadingInfoEntry 167}
	sensorReading167 OBJECT-TYPE
	  SYNTAX    DisplayString 
	  MAX-ACCESS  read-only
	  STATUS   current
	  DESCRIPTION 
	   ""
	  ::= {sensorReadingInfoEntry 168}
	sensorReading168 OBJECT-TYPE
	  SYNTAX    DisplayString 
	  MAX-ACCESS  read-only
	  STATUS   current
	  DESCRIPTION 
	   ""
	  ::= {sensorReadingInfoEntry 169}
	sensorReading169 OBJECT-TYPE
	  SYNTAX    DisplayString 
	  MAX-ACCESS  read-only
	  STATUS   current
	  DESCRIPTION 
	   ""
	  ::= {sensorReadingInfoEntry 170}
	  
	 
	sensorReading170 OBJECT-TYPE
	  SYNTAX    DisplayString 
	  MAX-ACCESS  read-only
	  STATUS   current
	  DESCRIPTION 
	   ""
	  ::= {sensorReadingInfoEntry 171}
	sensorReading171 OBJECT-TYPE
	  SYNTAX    DisplayString 
	  MAX-ACCESS  read-only
	  STATUS   current
	  DESCRIPTION 
	   ""
	  ::= {sensorReadingInfoEntry 172}
	sensorReading172 OBJECT-TYPE
	  SYNTAX    DisplayString 
	  MAX-ACCESS  read-only
	  STATUS   current
	  DESCRIPTION 
	   ""
	  ::= {sensorReadingInfoEntry 173}
	sensorReading173 OBJECT-TYPE
	  SYNTAX    DisplayString 
	  MAX-ACCESS  read-only
	  STATUS   current
	  DESCRIPTION 
	   ""
	  ::= {sensorReadingInfoEntry 174}
	sensorReading174 OBJECT-TYPE
	  SYNTAX    DisplayString 
	  MAX-ACCESS  read-only
	  STATUS   current
	  DESCRIPTION 
	   ""
	  ::= {sensorReadingInfoEntry 175}
	sensorReading175 OBJECT-TYPE
	  SYNTAX    DisplayString 
	  MAX-ACCESS  read-only
	  STATUS   current
	  DESCRIPTION 
	   ""
	  ::= {sensorReadingInfoEntry 176}
	sensorReading176 OBJECT-TYPE
	  SYNTAX    DisplayString 
	  MAX-ACCESS  read-only
	  STATUS   current
	  DESCRIPTION 
	   ""
	  ::= {sensorReadingInfoEntry 177}
	sensorReading177 OBJECT-TYPE
	  SYNTAX    DisplayString 
	  MAX-ACCESS  read-only
	  STATUS   current
	  DESCRIPTION 
	   ""
	  ::= {sensorReadingInfoEntry 178}
	sensorReading178 OBJECT-TYPE
	  SYNTAX    DisplayString 
	  MAX-ACCESS  read-only
	  STATUS   current
	  DESCRIPTION 
	   ""
	  ::= {sensorReadingInfoEntry 179}
	sensorReading179 OBJECT-TYPE
	  SYNTAX    DisplayString 
	  MAX-ACCESS  read-only
	  STATUS   current
	  DESCRIPTION 
	   ""
	  ::= {sensorReadingInfoEntry 180}
	 
	 
	sensorReading180 OBJECT-TYPE
	  SYNTAX    DisplayString 
	  MAX-ACCESS  read-only
	  STATUS   current
	  DESCRIPTION 
	   ""
	  ::= {sensorReadingInfoEntry 181}
	sensorReading181 OBJECT-TYPE
	  SYNTAX    DisplayString 
	  MAX-ACCESS  read-only
	  STATUS   current
	  DESCRIPTION 
	   ""
	  ::= {sensorReadingInfoEntry 182}
	sensorReading182 OBJECT-TYPE
	  SYNTAX    DisplayString 
	  MAX-ACCESS  read-only
	  STATUS   current
	  DESCRIPTION 
	   ""
	  ::= {sensorReadingInfoEntry 183}
	sensorReading183 OBJECT-TYPE
	  SYNTAX    DisplayString 
	  MAX-ACCESS  read-only
	  STATUS   current
	  DESCRIPTION 
	   ""
	  ::= {sensorReadingInfoEntry 184}
	sensorReading184 OBJECT-TYPE
	  SYNTAX    DisplayString 
	  MAX-ACCESS  read-only
	  STATUS   current
	  DESCRIPTION 
	   ""
	  ::= {sensorReadingInfoEntry 185}
	sensorReading185 OBJECT-TYPE
	  SYNTAX    DisplayString 
	  MAX-ACCESS  read-only
	  STATUS   current
	  DESCRIPTION 
	   ""
	  ::= {sensorReadingInfoEntry 186}
	sensorReading186 OBJECT-TYPE
	  SYNTAX    DisplayString 
	  MAX-ACCESS  read-only
	  STATUS   current
	  DESCRIPTION 
	   ""
	  ::= {sensorReadingInfoEntry 187}
	sensorReading187 OBJECT-TYPE
	  SYNTAX    DisplayString 
	  MAX-ACCESS  read-only
	  STATUS   current
	  DESCRIPTION 
	   ""
	  ::= {sensorReadingInfoEntry 188}
	sensorReading188 OBJECT-TYPE
	  SYNTAX    DisplayString 
	  MAX-ACCESS  read-only
	  STATUS   current
	  DESCRIPTION 
	   ""
	  ::= {sensorReadingInfoEntry 189}
	sensorReading189 OBJECT-TYPE
	  SYNTAX    DisplayString 
	  MAX-ACCESS  read-only
	  STATUS   current
	  DESCRIPTION 
	   ""
	  ::= {sensorReadingInfoEntry 190}
	  
	 
	sensorReading190 OBJECT-TYPE
	  SYNTAX    DisplayString 
	  MAX-ACCESS  read-only
	  STATUS   current
	  DESCRIPTION 
	   ""
	  ::= {sensorReadingInfoEntry 191}
	sensorReading191 OBJECT-TYPE
	  SYNTAX    DisplayString 
	  MAX-ACCESS  read-only
	  STATUS   current
	  DESCRIPTION 
	   ""
	  ::= {sensorReadingInfoEntry 192}
	sensorReading192 OBJECT-TYPE
	  SYNTAX    DisplayString 
	  MAX-ACCESS  read-only
	  STATUS   current
	  DESCRIPTION 
	   ""
	  ::= {sensorReadingInfoEntry 193}
	sensorReading193 OBJECT-TYPE
	  SYNTAX    DisplayString 
	  MAX-ACCESS  read-only
	  STATUS   current
	  DESCRIPTION 
	   ""
	  ::= {sensorReadingInfoEntry 194}
	sensorReading194 OBJECT-TYPE
	  SYNTAX    DisplayString 
	  MAX-ACCESS  read-only
	  STATUS   current
	  DESCRIPTION 
	   ""
	  ::= {sensorReadingInfoEntry 195}
	sensorReading195 OBJECT-TYPE
	  SYNTAX    DisplayString 
	  MAX-ACCESS  read-only
	  STATUS   current
	  DESCRIPTION 
	   ""
	  ::= {sensorReadingInfoEntry 196}
	sensorReading196 OBJECT-TYPE
	  SYNTAX    DisplayString 
	  MAX-ACCESS  read-only
	  STATUS   current
	  DESCRIPTION 
	   ""
	  ::= {sensorReadingInfoEntry 197}
	sensorReading197 OBJECT-TYPE
	  SYNTAX    DisplayString 
	  MAX-ACCESS  read-only
	  STATUS   current
	  DESCRIPTION 
	   ""
	  ::= {sensorReadingInfoEntry 198}
	sensorReading198 OBJECT-TYPE
	  SYNTAX    DisplayString 
	  MAX-ACCESS  read-only
	  STATUS   current
	  DESCRIPTION 
	   ""
	  ::= {sensorReadingInfoEntry 199}
	sensorReading199 OBJECT-TYPE
	  SYNTAX    DisplayString 
	  MAX-ACCESS  read-only
	  STATUS   current
	  DESCRIPTION 
	   ""
	  ::= {sensorReadingInfoEntry 200}
	sensorReading200 OBJECT-TYPE
	  SYNTAX    DisplayString 
	  MAX-ACCESS  read-only
	  STATUS   current
	  DESCRIPTION 
	   ""
	  ::= {sensorReadingInfoEntry 201}
	sensorReading201 OBJECT-TYPE
	  SYNTAX    DisplayString 
	  MAX-ACCESS  read-only
	  STATUS   current
	  DESCRIPTION 
	   ""
	  ::= {sensorReadingInfoEntry 202}
	sensorReading202 OBJECT-TYPE
	  SYNTAX    DisplayString 
	  MAX-ACCESS  read-only
	  STATUS   current
	  DESCRIPTION 
	   ""
	  ::= {sensorReadingInfoEntry 203}
	sensorReading203 OBJECT-TYPE
	  SYNTAX    DisplayString 
	  MAX-ACCESS  read-only
	  STATUS   current
	  DESCRIPTION 
	   ""
	  ::= {sensorReadingInfoEntry 204}
	sensorReading204 OBJECT-TYPE
	  SYNTAX    DisplayString 
	  MAX-ACCESS  read-only
	  STATUS   current
	  DESCRIPTION 
	   ""
	  ::= {sensorReadingInfoEntry 205}
	sensorReading205 OBJECT-TYPE
	  SYNTAX    DisplayString 
	  MAX-ACCESS  read-only
	  STATUS   current
	  DESCRIPTION 
	   ""
	  ::= {sensorReadingInfoEntry 206}
	sensorReading206 OBJECT-TYPE
	  SYNTAX    DisplayString 
	  MAX-ACCESS  read-only
	  STATUS   current
	  DESCRIPTION 
	   ""
	  ::= {sensorReadingInfoEntry 207}
	sensorReading207 OBJECT-TYPE
	  SYNTAX    DisplayString 
	  MAX-ACCESS  read-only
	  STATUS   current
	  DESCRIPTION 
	   ""
	  ::= {sensorReadingInfoEntry 208}
	sensorReading208 OBJECT-TYPE
	  SYNTAX    DisplayString 
	  MAX-ACCESS  read-only
	  STATUS   current
	  DESCRIPTION 
	   ""
	  ::= {sensorReadingInfoEntry 209}
	sensorReading209 OBJECT-TYPE
	  SYNTAX    DisplayString 
	  MAX-ACCESS  read-only
	  STATUS   current
	  DESCRIPTION 
	   ""
	  ::= {sensorReadingInfoEntry 210}
	  
	 
	sensorReading210 OBJECT-TYPE
	  SYNTAX    DisplayString 
	  MAX-ACCESS  read-only
	  STATUS   current
	  DESCRIPTION 
	   ""
	  ::= {sensorReadingInfoEntry 211}
	sensorReading211 OBJECT-TYPE
	  SYNTAX    DisplayString 
	  MAX-ACCESS  read-only
	  STATUS   current
	  DESCRIPTION 
	   ""
	  ::= {sensorReadingInfoEntry 212}
	sensorReading212 OBJECT-TYPE
	  SYNTAX    DisplayString 
	  MAX-ACCESS  read-only
	  STATUS   current
	  DESCRIPTION 
	   ""
	  ::= {sensorReadingInfoEntry 213}
	sensorReading213 OBJECT-TYPE
	  SYNTAX    DisplayString 
	  MAX-ACCESS  read-only
	  STATUS   current
	  DESCRIPTION 
	   ""
	  ::= {sensorReadingInfoEntry 214}
	sensorReading214 OBJECT-TYPE
	  SYNTAX    DisplayString 
	  MAX-ACCESS  read-only
	  STATUS   current
	  DESCRIPTION 
	   ""
	  ::= {sensorReadingInfoEntry 215}
	sensorReading215 OBJECT-TYPE
	  SYNTAX    DisplayString 
	  MAX-ACCESS  read-only
	  STATUS   current
	  DESCRIPTION 
	   ""
	  ::= {sensorReadingInfoEntry 216}
	sensorReading216 OBJECT-TYPE
	  SYNTAX    DisplayString 
	  MAX-ACCESS  read-only
	  STATUS   current
	  DESCRIPTION 
	   ""
	  ::= {sensorReadingInfoEntry 217}
	sensorReading217 OBJECT-TYPE
	  SYNTAX    DisplayString 
	  MAX-ACCESS  read-only
	  STATUS   current
	  DESCRIPTION 
	   ""
	  ::= {sensorReadingInfoEntry 218}
	sensorReading218 OBJECT-TYPE
	  SYNTAX    DisplayString 
	  MAX-ACCESS  read-only
	  STATUS   current
	  DESCRIPTION 
	   ""
	  ::= {sensorReadingInfoEntry 219}
	sensorReading219 OBJECT-TYPE
	  SYNTAX    DisplayString 
	  MAX-ACCESS  read-only
	  STATUS   current
	  DESCRIPTION 
	   ""
	  ::= {sensorReadingInfoEntry 220}
	  
	 
	sensorReading220 OBJECT-TYPE
	  SYNTAX    DisplayString 
	  MAX-ACCESS  read-only
	  STATUS   current
	  DESCRIPTION 
	   ""
	  ::= {sensorReadingInfoEntry 221}
	sensorReading221 OBJECT-TYPE
	  SYNTAX    DisplayString 
	  MAX-ACCESS  read-only
	  STATUS   current
	  DESCRIPTION 
	   ""
	  ::= {sensorReadingInfoEntry 222}
	sensorReading222 OBJECT-TYPE
	  SYNTAX    DisplayString 
	  MAX-ACCESS  read-only
	  STATUS   current
	  DESCRIPTION 
	   ""
	  ::= {sensorReadingInfoEntry 223}
	sensorReading223 OBJECT-TYPE
	  SYNTAX    DisplayString 
	  MAX-ACCESS  read-only
	  STATUS   current
	  DESCRIPTION 
	   ""
	  ::= {sensorReadingInfoEntry 224}
	sensorReading224 OBJECT-TYPE
	  SYNTAX    DisplayString 
	  MAX-ACCESS  read-only
	  STATUS   current
	  DESCRIPTION 
	   ""
	  ::= {sensorReadingInfoEntry 225}
	sensorReading225 OBJECT-TYPE
	  SYNTAX    DisplayString 
	  MAX-ACCESS  read-only
	  STATUS   current
	  DESCRIPTION 
	   ""
	  ::= {sensorReadingInfoEntry 226}
	sensorReading226 OBJECT-TYPE
	  SYNTAX    DisplayString 
	  MAX-ACCESS  read-only
	  STATUS   current
	  DESCRIPTION 
	   ""
	  ::= {sensorReadingInfoEntry 227}
	sensorReading227 OBJECT-TYPE
	  SYNTAX    DisplayString 
	  MAX-ACCESS  read-only
	  STATUS   current
	  DESCRIPTION 
	   ""
	  ::= {sensorReadingInfoEntry 228}
	sensorReading228 OBJECT-TYPE
	  SYNTAX    DisplayString 
	  MAX-ACCESS  read-only
	  STATUS   current
	  DESCRIPTION 
	   ""
	  ::= {sensorReadingInfoEntry 229}
	sensorReading229 OBJECT-TYPE
	  SYNTAX    DisplayString 
	  MAX-ACCESS  read-only
	  STATUS   current
	  DESCRIPTION 
	   ""
	  ::= {sensorReadingInfoEntry 230}
	  
	 
	sensorReading230 OBJECT-TYPE
	  SYNTAX    DisplayString 
	  MAX-ACCESS  read-only
	  STATUS   current
	  DESCRIPTION 
	   ""
	  ::= {sensorReadingInfoEntry 231}
	sensorReading231 OBJECT-TYPE
	  SYNTAX    DisplayString 
	  MAX-ACCESS  read-only
	  STATUS   current
	  DESCRIPTION 
	   ""
	  ::= {sensorReadingInfoEntry 232}
	sensorReading232 OBJECT-TYPE
	  SYNTAX    DisplayString 
	  MAX-ACCESS  read-only
	  STATUS   current
	  DESCRIPTION 
	   ""
	  ::= {sensorReadingInfoEntry 233}
	sensorReading233 OBJECT-TYPE
	  SYNTAX    DisplayString 
	  MAX-ACCESS  read-only
	  STATUS   current
	  DESCRIPTION 
	   ""
	  ::= {sensorReadingInfoEntry 234}
	sensorReading234 OBJECT-TYPE
	  SYNTAX    DisplayString 
	  MAX-ACCESS  read-only
	  STATUS   current
	  DESCRIPTION 
	   ""
	  ::= {sensorReadingInfoEntry 235}
	sensorReading235 OBJECT-TYPE
	  SYNTAX    DisplayString 
	  MAX-ACCESS  read-only
	  STATUS   current
	  DESCRIPTION 
	   ""
	  ::= {sensorReadingInfoEntry 236}
	sensorReading236 OBJECT-TYPE
	  SYNTAX    DisplayString 
	  MAX-ACCESS  read-only
	  STATUS   current
	  DESCRIPTION 
	   ""
	  ::= {sensorReadingInfoEntry 237}
	sensorReading237 OBJECT-TYPE
	  SYNTAX    DisplayString 
	  MAX-ACCESS  read-only
	  STATUS   current
	  DESCRIPTION 
	   ""
	  ::= {sensorReadingInfoEntry 238}
	sensorReading238 OBJECT-TYPE
	  SYNTAX    DisplayString 
	  MAX-ACCESS  read-only
	  STATUS   current
	  DESCRIPTION 
	   ""
	  ::= {sensorReadingInfoEntry 239}
	sensorReading239 OBJECT-TYPE
	  SYNTAX    DisplayString 
	  MAX-ACCESS  read-only
	  STATUS   current
	  DESCRIPTION 
	   ""
	  ::= {sensorReadingInfoEntry 240}
	  
	 
	sensorReading240 OBJECT-TYPE
	  SYNTAX    DisplayString 
	  MAX-ACCESS  read-only
	  STATUS   current
	  DESCRIPTION 
	   ""
	  ::= {sensorReadingInfoEntry 241}
	sensorReading241 OBJECT-TYPE
	  SYNTAX    DisplayString 
	  MAX-ACCESS  read-only
	  STATUS   current
	  DESCRIPTION 
	   ""
	  ::= {sensorReadingInfoEntry 242}
	sensorReading242 OBJECT-TYPE
	  SYNTAX    DisplayString 
	  MAX-ACCESS  read-only
	  STATUS   current
	  DESCRIPTION 
	   ""
	  ::= {sensorReadingInfoEntry 243}
	sensorReading243 OBJECT-TYPE
	  SYNTAX    DisplayString 
	  MAX-ACCESS  read-only
	  STATUS   current
	  DESCRIPTION 
	   ""
	  ::= {sensorReadingInfoEntry 244}
	sensorReading244 OBJECT-TYPE
	  SYNTAX    DisplayString 
	  MAX-ACCESS  read-only
	  STATUS   current
	  DESCRIPTION 
	   ""
	  ::= {sensorReadingInfoEntry 245}
	sensorReading245 OBJECT-TYPE
	  SYNTAX    DisplayString 
	  MAX-ACCESS  read-only
	  STATUS   current
	  DESCRIPTION 
	   ""
	  ::= {sensorReadingInfoEntry 246}
	sensorReading246 OBJECT-TYPE
	  SYNTAX    DisplayString 
	  MAX-ACCESS  read-only
	  STATUS   current
	  DESCRIPTION 
	   ""
	  ::= {sensorReadingInfoEntry 247}
	sensorReading247 OBJECT-TYPE
	  SYNTAX    DisplayString 
	  MAX-ACCESS  read-only
	  STATUS   current
	  DESCRIPTION 
	   ""
	  ::= {sensorReadingInfoEntry 248}
	sensorReading248 OBJECT-TYPE
	  SYNTAX    DisplayString 
	  MAX-ACCESS  read-only
	  STATUS   current
	  DESCRIPTION 
	   ""
	  ::= {sensorReadingInfoEntry 249}
	sensorReading249 OBJECT-TYPE
	  SYNTAX    DisplayString 
	  MAX-ACCESS  read-only
	  STATUS   current
	  DESCRIPTION 
	   ""
	  ::= {sensorReadingInfoEntry 250}
	  
	 
	sensorReading250 OBJECT-TYPE
	  SYNTAX    DisplayString 
	  MAX-ACCESS  read-only
	  STATUS   current
	  DESCRIPTION 
	   ""
	  ::= {sensorReadingInfoEntry 251}
	sensorReading251 OBJECT-TYPE
	  SYNTAX    DisplayString 
	  MAX-ACCESS  read-only
	  STATUS   current
	  DESCRIPTION 
	   ""
	  ::= {sensorReadingInfoEntry 252}
	sensorReading252 OBJECT-TYPE
	  SYNTAX    DisplayString 
	  MAX-ACCESS  read-only
	  STATUS   current
	  DESCRIPTION 
	   ""
	  ::= {sensorReadingInfoEntry 253}
	sensorReading253 OBJECT-TYPE
	  SYNTAX    DisplayString 
	  MAX-ACCESS  read-only
	  STATUS   current
	  DESCRIPTION 
	   ""
	  ::= {sensorReadingInfoEntry 254}
	sensorReading254 OBJECT-TYPE
	  SYNTAX    DisplayString 
	  MAX-ACCESS  read-only
	  STATUS   current
	  DESCRIPTION 
	   ""
	  ::= {sensorReadingInfoEntry 255}
	sensorReading255 OBJECT-TYPE
	  SYNTAX    DisplayString 
	  MAX-ACCESS  read-only
	  STATUS   current
	  DESCRIPTION 
	   ""
	  ::= {sensorReadingInfoEntry 256}
	sensorReading256 OBJECT-TYPE
	  SYNTAX    DisplayString 
	  MAX-ACCESS  read-only
	  STATUS   current
	  DESCRIPTION 
	   ""
	  ::= {sensorReadingInfoEntry 257}
	
--sensorReadingInfoTable end
--networkCardInfo start
	networkCardInfoTable OBJECT-TYPE
		SYNTAX SEQUENCE OF NetworkCardInfoEntry
		MAX-ACCESS not-accessible
		STATUS current
		DESCRIPTION
			""
		::= { serverAssetInfo 29 }
	networkCardInfoEntry OBJECT-TYPE
		SYNTAX NetworkCardInfoEntry
		MAX-ACCESS not-accessible
		STATUS current
		DESCRIPTION
			""
		INDEX { networkCardInfoIndex }
		::= { networkCardInfoTable 1 }
	NetworkCardInfoEntry ::=
		SEQUENCE {
			networkCardInfoIndex		Integer32,
			networkCardInfoNo			OCTET STRING,
			networkCardInfoSlot			OCTET STRING,
			networkCardInfoBusNo		OCTET STRING,
			networkCardInfoDevNo		OCTET STRING,
			networkCardInfoFuncNo		OCTET STRING,
			networkCardInfoMac			 OCTET STRING,
			networkCardInfoManufacturer		OCTET STRING,
			networkCardInfoDescription	OCTET STRING,
			networkCardInfoPortName 		Integer32,
			networkCardInfoPortType		OCTET STRING,
			networkCardInfoInterface	OCTET STRING,
			networkCardInfoPortSpeed  	OCTET STRING,
			networkCardInFwVersion		OCTET STRING
		}
	networkCardInfoIndex OBJECT-TYPE
		SYNTAX Integer32
		MAX-ACCESS read-only
		STATUS current
		DESCRIPTION
			""
		::= { networkCardInfoEntry 1 }
	networkCardInfoNo OBJECT-TYPE
		SYNTAX OCTET STRING
		MAX-ACCESS read-only
		STATUS current
		DESCRIPTION
			""
		::= { networkCardInfoEntry 2 }
	networkCardInfoSlot OBJECT-TYPE
		SYNTAX OCTET STRING
		MAX-ACCESS read-only
		STATUS current
		DESCRIPTION
			""
		::= { networkCardInfoEntry 3 }
	networkCardInfoBusNo OBJECT-TYPE
		SYNTAX OCTET STRING
		MAX-ACCESS read-only
		STATUS current
		DESCRIPTION
			""
		::= { networkCardInfoEntry 4 }
	networkCardInfoDevNo OBJECT-TYPE
		SYNTAX OCTET STRING
		MAX-ACCESS read-only
		STATUS current
		DESCRIPTION
			""
		::= { networkCardInfoEntry 5 }
	networkCardInfoFuncNo OBJECT-TYPE
		SYNTAX OCTET STRING
		MAX-ACCESS read-only
		STATUS current
		DESCRIPTION
			""
		::= { networkCardInfoEntry 6 }
	networkCardInfoMac OBJECT-TYPE
		SYNTAX OCTET STRING
		MAX-ACCESS read-only
		STATUS current
		DESCRIPTION
			""
		::= { networkCardInfoEntry 7 }
	networkCardInfoManufacturer OBJECT-TYPE
		SYNTAX OCTET STRING
		MAX-ACCESS read-only
		STATUS current
		DESCRIPTION
			""
		::= { networkCardInfoEntry 8 }
	networkCardInfoDescription OBJECT-TYPE
		SYNTAX OCTET STRING

		MAX-ACCESS read-only
		STATUS current
		DESCRIPTION
			""
		::= { networkCardInfoEntry 9 }
	networkCardInfoPortName OBJECT-TYPE
		SYNTAX Integer32
		MAX-ACCESS read-only
		STATUS current
		DESCRIPTION
			""
		::= { networkCardInfoEntry 10 }
	networkCardInfoPortType OBJECT-TYPE
		SYNTAX OCTET STRING
		MAX-ACCESS read-only
		STATUS current
		DESCRIPTION
			""
		::= { networkCardInfoEntry 11 }
	networkCardInfoInterface OBJECT-TYPE
		SYNTAX OCTET STRING
		MAX-ACCESS read-only
		STATUS current
		DESCRIPTION
			""
		::= { networkCardInfoEntry 12 }
	networkCardInfoPortSpeed OBJECT-TYPE
		SYNTAX OCTET STRING

		MAX-ACCESS read-only
		STATUS current
		DESCRIPTION
			""
		::= { networkCardInfoEntry 13 }
	networkCardInFwVersion OBJECT-TYPE
		SYNTAX OCTET STRING
		MAX-ACCESS read-only
		STATUS current
		DESCRIPTION
			""
		::= { networkCardInfoEntry 14 }
--networkCardInfo end
--gpuInfoTable start
	gpuInfoTable OBJECT-TYPE
		SYNTAX SEQUENCE OF GpuInfoEntry
		MAX-ACCESS not-accessible
		STATUS current
		DESCRIPTION
			""
		::= { serverAssetInfo 30 }
	gpuInfoEntry OBJECT-TYPE
		SYNTAX GpuInfoEntry
		MAX-ACCESS not-accessible
		STATUS current
		DESCRIPTION
			""
		INDEX { gpuIndex }
		::= { gpuInfoTable 1 }
	GpuInfoEntry ::=
		SEQUENCE {
			gpuIndex			Integer32,
			gpuDevice			OCTET STRING,
			gpuCpuResource		OCTET STRING,
			gpuInterface		OCTET STRING,
			gpuTemperature1		OCTET STRING,
			gpuTemperature2		OCTET STRING,
			gpuTotalPower		OCTET STRING,
			gpuSerialNumber		OCTET STRING,
			gpuFWVersion		OCTET STRING
		}
	gpuIndex OBJECT-TYPE
		SYNTAX Integer32
		MAX-ACCESS read-only
		STATUS current
		DESCRIPTION
			""
		::= { gpuInfoEntry 1 }
	gpuDevice OBJECT-TYPE
		SYNTAX OCTET STRING
		MAX-ACCESS read-only
		STATUS current
		DESCRIPTION
			""
		::= { gpuInfoEntry 2 }
	gpuCpuResource OBJECT-TYPE
		SYNTAX OCTET STRING
		MAX-ACCESS read-only
		STATUS current
		DESCRIPTION
			""
		::= { gpuInfoEntry 3 }
	gpuInterface OBJECT-TYPE
		SYNTAX OCTET STRING
		MAX-ACCESS read-only
		STATUS current
		DESCRIPTION
			""
		::= { gpuInfoEntry 4 }
	gpuTemperature1 OBJECT-TYPE
		SYNTAX OCTET STRING
		MAX-ACCESS read-only
		STATUS current
		DESCRIPTION
			""
		::= { gpuInfoEntry 5 }
	gpuTemperature2 OBJECT-TYPE
		SYNTAX OCTET STRING
		MAX-ACCESS read-only
		STATUS current
		DESCRIPTION
			""
		::= { gpuInfoEntry 6 }
	gpuTotalPower OBJECT-TYPE
		SYNTAX OCTET STRING
		MAX-ACCESS read-only
		STATUS current
		DESCRIPTION
			""
		::= { gpuInfoEntry 7 }
	gpuSerialNumber OBJECT-TYPE
		SYNTAX OCTET STRING
		MAX-ACCESS read-only
		STATUS current
		DESCRIPTION
			""
		::= { gpuInfoEntry 8 }
	gpuFWVersion OBJECT-TYPE
		SYNTAX OCTET STRING
		MAX-ACCESS read-only
		STATUS current
		DESCRIPTION
			""
		::= { gpuInfoEntry 9 }

--gpuInfoTable end
--networkInterfaceTable start
	networkInterfaceTable	OBJECT-TYPE
	    SYNTAX     SEQUENCE OF NetworkInterfaceEntry
	    MAX-ACCESS not-accessible
	    STATUS     current
	    DESCRIPTION
	    "
	    The table of dedicated interface information relevant to this entity's dedicated interface.
	    "
		::= {serverBmcInfo 1}
	networkInterfaceEntry OBJECT-TYPE
	    SYNTAX     NetworkInterfaceEntry
	    MAX-ACCESS not-accessible
	    STATUS     current
	    DESCRIPTION
	           "The dedicated interface information associated with the dedicated interface of this entry."
	    INDEX   { 
				  networkInterfaceIndex
	            }
	    ::= { networkInterfaceTable 1 }   
	
	NetworkInterfaceEntry ::= SEQUENCE {
		networkInterfaceIndex					Integer32,
	    networkInterfaceName					DisplayString,
	    networkInterfaceEnable					Integer32,
		networkInterfaceMACAddress				DisplayString,
		networkInterfaceIPv4Enable				Integer32,
	    networkInterfaceIPv4ObtainMethodConf	Integer32,
	    networkInterfaceIPv4Address				IpAddress,
	    networkInterfaceIPv4SubnetMask			IpAddress,
	    networkInterfaceIPv4Gateway				IpAddress,
		networkInterfaceIPv6Enable				Integer32,
	    networkInterfaceIPv6ObtainMethodConf	Integer32,
	    networkInterfaceIPv6Index				Integer32,
	    networkInterfaceIPv6Address				DisplayString,
	    networkInterfaceIPv6Prefix				Integer32,
	    networkInterfaceIPv6Gateway             DisplayString,
		networkInterfaceVlanEnable				Integer32,
		networkInterfaceVlanID					Integer32,
		networkInterfaceVlanPriority			Integer32
	}
	networkInterfaceIndex  OBJECT-TYPE
		SYNTAX 			Integer32
		MAX-ACCESS		read-only
		STATUS			current
		DESCRIPTION 
		"  
			The index value which uniquely identifies 
			the interface to which this entry is applicable.
		"
		::= {networkInterfaceEntry 1}           
	         
	networkInterfaceName OBJECT-TYPE
		SYNTAX 			DisplayString 
		MAX-ACCESS		read-only
		STATUS			current
		DESCRIPTION 
		"
			The interface name associated with the dedicated interface of this entry.
		"
		::= {networkInterfaceEntry 2} 
	
	networkInterfaceEnable OBJECT-TYPE
		SYNTAX 			Integer32{
						disable(0),
						enable(1)
					} 
		MAX-ACCESS		read-write
		STATUS			current
		DESCRIPTION 
		"
			The dedicated interface enable associated with the dedicated interface of this entry.
		"
		::= {networkInterfaceEntry 3}  
	
	networkInterfaceMACAddress OBJECT-TYPE
		SYNTAX 			DisplayString 
		MAX-ACCESS		read-only
		STATUS			current
		DESCRIPTION 
		"
			The MAC address associated with the dedicated interface of this entry.
		"
		::= {networkInterfaceEntry 4} 

	networkInterfaceIPv4Enable OBJECT-TYPE
		SYNTAX 			Integer32{
						disable(0),
						enable(1)
					} 
		MAX-ACCESS		read-write
		STATUS			current
		DESCRIPTION 
		"
			Enable ipv4 network or not of this entry.
		"
		::= {networkInterfaceEntry 5} 

	networkInterfaceIPv4ObtainMethodConf  OBJECT-TYPE
		SYNTAX 			Integer32{
						static(1),
						dhcp(2)
		} 
		MAX-ACCESS		read-write
		STATUS			current
		DESCRIPTION 
		"
			The IPv4 Obtain Method associated with the dedicated interface of this entry.
			1 for static IP.
			2 for DHCP.
		"
		::= {networkInterfaceEntry 6} 
	
	networkInterfaceIPv4Address OBJECT-TYPE
		SYNTAX 			IpAddress 
		MAX-ACCESS		read-write
		STATUS			current
		DESCRIPTION 
		"
			The IPv4 address associated with the dedicated interface of this entry.
			If you want to set a static IP address and the gateway is invalid for the new IP address, 
			you need to first set the IPv4Gateway.
		"
		::= {networkInterfaceEntry 7}
	networkInterfaceIPv4SubnetMask OBJECT-TYPE
		SYNTAX 			IpAddress 
		MAX-ACCESS		read-write
		STATUS			current
		DESCRIPTION 
		"
			The IPv4 subnet mask associated with the dedicated interface of this entry.
		"
		::= {networkInterfaceEntry 8}    
	   
	networkInterfaceIPv4Gateway OBJECT-TYPE
		SYNTAX 			IpAddress 
		MAX-ACCESS		read-write
		STATUS			current
		DESCRIPTION 
		"
			The IPv4 Default gateway associated with the dedicated interface of this entry.
			If you want to set a static IP address and the gateway is invalid for the new IP address, 
			you need to first set the IPv4Gateway.
		"
		::= {networkInterfaceEntry 9}    
	networkInterfaceIPv6Enable OBJECT-TYPE
		SYNTAX 			Integer32{
						disable(0),
						enable(1)
					} 
		MAX-ACCESS		read-write
		STATUS			current
		DESCRIPTION 
		"
			Enable ipv6 network or not of this entry.
		"
		::= {networkInterfaceEntry 10} 

	networkInterfaceIPv6ObtainMethodConf  OBJECT-TYPE
		SYNTAX 			Integer32{
						static(1),
						dhcp(2)
		} 
		MAX-ACCESS		read-write
		STATUS			current
		DESCRIPTION 
		"
			The IPv6 Obtain Method associated with the dedicated interface of this entry.
			1 for static IP.
			2 for DHCP.
		"
		::= {networkInterfaceEntry 11} 	
	networkInterfaceIPv6Index OBJECT-TYPE
		SYNTAX 			Integer32 
		MAX-ACCESS		read-only
		STATUS			current
		DESCRIPTION 
		"
			The IPv6 index associated with the dedicated interface of this entry.
		"
		::= {networkInterfaceEntry 12} 

	networkInterfaceIPv6Address  OBJECT-TYPE
		SYNTAX 			DisplayString
		MAX-ACCESS		read-only
		STATUS			current
		DESCRIPTION 
		"
			The IPv6 address associated with the dedicated interface of this entry.
		"
		::= {networkInterfaceEntry 13} 
		
	networkInterfaceIPv6Prefix  OBJECT-TYPE
		SYNTAX 			Integer32
		MAX-ACCESS		read-only
		STATUS			current
		DESCRIPTION 
		"
			The IPv6 prefix associated with the dedicated interface of this entry.
		"
		::= {networkInterfaceEntry 14}
	networkInterfaceIPv6Gateway OBJECT-TYPE
		SYNTAX 			DisplayString 
		MAX-ACCESS		read-write
		STATUS			current
		DESCRIPTION 
		"
			The IPv6 Default gateway associated with the dedicated interface of this entry.
			If you want to set static ipaddress and the gateway is invalid for the new ipaddress,
			you should set the gateway to 0000.0000.0000.0000.0000.0000.0000.0000 or 0000::0000 and so on.
		"
		::= {networkInterfaceEntry 15} 
	networkInterfaceVlanEnable OBJECT-TYPE
		SYNTAX 			Integer32{
						disable(0),
						enable(1)
					} 
		MAX-ACCESS		read-write
		STATUS			current
		DESCRIPTION 
		"
			The vlan enable status associated with the dedicated interface of this entry.
		"
		::= {networkInterfaceEntry 16}
	
	networkInterfaceVlanID OBJECT-TYPE
		SYNTAX 			Integer32
		MAX-ACCESS		read-write
		STATUS			current
		DESCRIPTION 
		"
			The vlan ID associated with the dedicated interface of this entry.
			If you want to confiure the Vlan ID, make sure you had enable the Vlan.
		"
		::= {networkInterfaceEntry 17}
	
	networkInterfaceVlanPriority OBJECT-TYPE
		SYNTAX 			Integer32
		MAX-ACCESS		read-write
		STATUS			current
		DESCRIPTION 
		"
			The vlan priority associated with the dedicated interface of this entry.
			If you want to confiure the Vlan priority, make sure you had enable the Vlan.
		"
		::= {networkInterfaceEntry 18}     
--networkInterfaceTable end
--networkSharedIPv6StaticTable start
	networkSharedIPv6StaticTable	OBJECT-TYPE
	    SYNTAX     SEQUENCE OF NetworkSharedIPv6StaticEntry
	    MAX-ACCESS not-accessible
	    STATUS     current
	    DESCRIPTION
	    "
	    The table of Shared interface information relevant to this entity's dedicated interface.
	    "
		::= {serverBmcInfo 2}
	networkSharedIPv6StaticEntry OBJECT-TYPE
	    SYNTAX     NetworkSharedIPv6StaticEntry
	    MAX-ACCESS not-accessible
	    STATUS     current
	    DESCRIPTION
	           "The Shared interface information associated with the dedicated interface of this entry."
	    INDEX   { 
				  networkSharedIPv6StaticEntryIndex	                
	            }
	    ::= { networkSharedIPv6StaticTable 1 }   
	
	NetworkSharedIPv6StaticEntry ::= SEQUENCE {
		networkSharedIPv6StaticEntryIndex	Integer32,
	    networkSharedIPv6StaticIndex		Integer32,
	    networkSharedIPv6StaticAddress		DisplayString,
	    networkSharedIPv6StaticPrefix		Integer32
	}
	networkSharedIPv6StaticEntryIndex  OBJECT-TYPE
		SYNTAX 			Integer32
		MAX-ACCESS		read-only
		STATUS			current
		DESCRIPTION 
		"  
			The index value which uniquely identifies 
			the interface to which this entry is applicable.
		"
		::= {networkSharedIPv6StaticEntry 1}    
	networkSharedIPv6StaticIndex  OBJECT-TYPE
		SYNTAX 			Integer32
		MAX-ACCESS		read-only
		STATUS			current
		DESCRIPTION 
		"  
			The IPv6 index associated with the dedicated interface of this entry.
		"
		::= {networkSharedIPv6StaticEntry 2}   
	networkSharedIPv6StaticAddress  OBJECT-TYPE
		SYNTAX 			DisplayString
		MAX-ACCESS		read-write
		STATUS			current
		DESCRIPTION 
		"
			The IPv6 address associated with the dedicated interface of this entry.
		"
		::= {networkSharedIPv6StaticEntry 3} 
		
	networkSharedIPv6StaticPrefix  OBJECT-TYPE
		SYNTAX 			Integer32
		MAX-ACCESS		read-write
		STATUS			current
		DESCRIPTION 
		"
			The IPv6 prefix associated with the dedicated interface of this entry.
		"
		::= {networkSharedIPv6StaticEntry 4}
		
--networkSharedIPv6StaticTable end
--networkDedicatedIPv6StaticTable start
	networkDedicatedIPv6StaticTable	OBJECT-TYPE
	    SYNTAX     SEQUENCE OF NetworkDedicatedIPv6StaticEntry
	    MAX-ACCESS not-accessible
	    STATUS     current
	    DESCRIPTION
	    "
	    The table of dedicated interface information relevant to this entity's dedicated interface.
	    "
		::= {serverBmcInfo 3}
	networkDedicatedIPv6StaticEntry OBJECT-TYPE
	    SYNTAX     NetworkDedicatedIPv6StaticEntry
	    MAX-ACCESS not-accessible
	    STATUS     current
	    DESCRIPTION
	           "The dedicated interface information associated with the dedicated interface of this entry."
	    INDEX   { 
				  networkDedicatedIPv6StaticEntryIndex	                
	            }
	    ::= { networkDedicatedIPv6StaticTable 1 }   
	
	NetworkDedicatedIPv6StaticEntry ::= SEQUENCE {
		networkDedicatedIPv6StaticEntryIndex	Integer32,
	    networkDedicatedIPv6StaticIndex			Integer32,
	    networkDedicatedIPv6StaticAddress		DisplayString,
	    networkDedicatedIPv6StaticPrefix		Integer32
	}
	networkDedicatedIPv6StaticEntryIndex  OBJECT-TYPE
		SYNTAX 			Integer32
		MAX-ACCESS		read-only
		STATUS			current
		DESCRIPTION 
		"  
			The index value which uniquely identifies 
			the interface to which this entry is applicable.
		"
		::= {networkDedicatedIPv6StaticEntry 1}    
	networkDedicatedIPv6StaticIndex  OBJECT-TYPE
		SYNTAX 			Integer32
		MAX-ACCESS		read-only
		STATUS			current
		DESCRIPTION 
		"
			The IPv6 index associated with the dedicated interface of this entry.
		"
		::= {networkDedicatedIPv6StaticEntry 2} 
	networkDedicatedIPv6StaticAddress  OBJECT-TYPE
		SYNTAX 			DisplayString
		MAX-ACCESS		read-write
		STATUS			current
		DESCRIPTION 
		"
			The IPv6 address associated with the dedicated interface of this entry.
		"
		::= {networkDedicatedIPv6StaticEntry 3} 
	networkDedicatedIPv6StaticPrefix  OBJECT-TYPE
		SYNTAX 			Integer32
		MAX-ACCESS		read-write
		STATUS			current
		DESCRIPTION 
		"
			The IPv6 prefix associated with the dedicated interface of this entry.
		"
		::= {networkDedicatedIPv6StaticEntry 4}
--networkDedicatedIPv6StaticTable end
--bmcNTPConf start
	bmcNTPServer1 OBJECT-TYPE
		SYNTAX 			DisplayString
		MAX-ACCESS		read-write
		STATUS			current
		DESCRIPTION 
		"
		The NTP server of the NTP conf.			
		"
		::= {bmcNTPConf 1} 

	bmcNTPServer2 OBJECT-TYPE
        SYNTAX          DisplayString
        MAX-ACCESS      read-write
        STATUS          current
        DESCRIPTION 
        "
        The NTP server of the NTP conf.         
        "
        ::= {bmcNTPConf 2} 
	bmcNTPDateTime  OBJECT-TYPE
		SYNTAX 			DisplayString
		MAX-ACCESS		read-only
		STATUS			current
		DESCRIPTION 
		"
		The date and time of the BMC.	
		"
		::= {bmcNTPConf 3} 
	bmcNTPAutoSync  OBJECT-TYPE
		SYNTAX 			Integer32{
						manual(0),
						auto(1)
		} 
		MAX-ACCESS		read-write
		STATUS			current
		DESCRIPTION 
		"
		The auto sync enable status of the NTP conf.	
		"
		::= {bmcNTPConf 4} 
	bmcNTPUTCTimezone OBJECT-TYPE
		SYNTAX 			DisplayString
		MAX-ACCESS		read-write
		STATUS			current
		DESCRIPTION 
		"
		The UTC time zone of the NTP config.	
		"
		::= {bmcNTPConf 5} 
	bmcNTPUTCSynchronizationPeriod OBJECT-TYPE
		SYNTAX 			Integer32
		MAX-ACCESS		read-write
		STATUS			current
		DESCRIPTION 
		"
		The synchronization period of the NTP config.	
		"
		::= {bmcNTPConf 6} 
--bmcNTPConf end
--bmcUserManagement start
	bmcUserConfTable	OBJECT-TYPE
	    SYNTAX     SEQUENCE OF BmcUserConfEntry
	    MAX-ACCESS not-accessible
	    STATUS     current
	    DESCRIPTION
	    "
	    The table of dedicated user conf information relevant to this entity's dedicated user conf.
	    "
		::= {bmcUserManagement 1}
	bmcUserConfEntry OBJECT-TYPE
	    SYNTAX     BmcUserConfEntry
	    MAX-ACCESS not-accessible
	    STATUS     current
	    DESCRIPTION
	           "The dedicated user conf information associated with the dedicated user conf of this entry."
	    INDEX   { 
				  bmcUserIndex                
	            }
	    ::= { bmcUserConfTable 1 }   
	
	BmcUserConfEntry ::= SEQUENCE {
		bmcUserIndex			Integer32,
	    bmcUserName				DisplayString,
		bmcUserPassword			DisplayString,
		bmcSNMPV3UserStatus		Integer32,
		bmcSNMPTYPE				Integer32,
		bmcSNMPV3UserAccess		Integer32,
	    bmcSNMPV3UserAuthProto	Integer32,
	    bmcSNMPV3UserPrivProto	Integer32,
		bmcUserGroupName		DisplayString,
		bmcEmailID				DisplayString
	}
	bmcUserIndex OBJECT-TYPE
		SYNTAX 			Integer32
		MAX-ACCESS		read-only
		STATUS			current
		DESCRIPTION 
		"
		The index associated with the dedicated interface of this entry.	
		"
		::= {bmcUserConfEntry 1}		
	bmcUserName OBJECT-TYPE
		SYNTAX 			DisplayString
		MAX-ACCESS		read-write
		STATUS			current
		DESCRIPTION 
		"
		The name of the SNMPv3 user you want to set.	
		"
		::= {bmcUserConfEntry 2}	
	bmcUserPassword OBJECT-TYPE
		SYNTAX 			DisplayString
		MAX-ACCESS		read-write
		STATUS			current
		DESCRIPTION 
		"
		The password of the SNMPV3 user which is used to set authentication and privacy.	
		"
		::= {bmcUserConfEntry 3}
	bmcSNMPV3UserStatus OBJECT-TYPE
		SYNTAX 			Integer32
						{
						disable(0),
						enable(1)
						}
		MAX-ACCESS		read-write
		STATUS			current
		DESCRIPTION 
		"
		The status of the SNMPV3 user.	
		"
		::= {bmcUserConfEntry 4}
	bmcSNMPTYPE OBJECT-TYPE
		SYNTAX 			Integer32{
						snmpv3(3)
		}
		MAX-ACCESS		read-only
		STATUS			current
		DESCRIPTION 
		"
		SNMP_TPYE, you can see the snmpv3.	
		3 for snmpv3.
		"
		::= {bmcUserConfEntry 5}
	bmcSNMPV3UserAccess OBJECT-TYPE
		SYNTAX 			Integer32{
						ro(1),
						rw(2)
		}
		MAX-ACCESS		read-write
		STATUS			current
		DESCRIPTION 
		"
		The access of the SNMPv3 user you want to set.	
		1 for read-only.
		2 for read-write.
		"
		::= {bmcUserConfEntry 6}
	bmcSNMPV3UserAuthProto OBJECT-TYPE
		SYNTAX 			Integer32{
						sha(1),
						md5(2),
						sha256(3),
						sha384(4),
						sha512(5)
		}
		MAX-ACCESS		read-write
		STATUS			current
		DESCRIPTION 
		"
		The authentication protocol of the SNMPv3 user , you can set 1 or 2 but not 0.	
		0 for without authentication protocol.
		1 for SHA.
		2 for MD5.
		3 for SHA256.
		4 for SHA384.
		5 for SHA512.
		"
		::= {bmcUserConfEntry 7}
	bmcSNMPV3UserPrivProto OBJECT-TYPE
		SYNTAX 			Integer32{
						des(1),
						aes(2)
		}
		MAX-ACCESS		read-write
		STATUS			current
		DESCRIPTION 
		"
		The privacy protocol of the SNMPv3 user.	
		0 for without privacy protocol.
		1 for DES.
		2 for AES.
		"
		::= {bmcUserConfEntry 8}
	bmcUserGroupName OBJECT-TYPE
		SYNTAX 			DisplayString									
		MAX-ACCESS		read-write
		STATUS			current
		DESCRIPTION 
		"
		The user group name of the user.
		You can set different user group name and need to enter the group name you have chosen, as shown below:
		Administrator
		Operator
		User
		'OEMGroup1'
		'OEMGroup2'
		'OMEGroup3'
		'OEMGroup4'
		'OEMGroup5'
		please enter the group name.
		"
		::= {bmcUserConfEntry 9}
	bmcEmailID OBJECT-TYPE
		SYNTAX 			DisplayString
		MAX-ACCESS		read-write
		STATUS			current
		DESCRIPTION 
		"
		The email id of the user.	
		"
		::= {bmcUserConfEntry 10}
	addBmcUser OBJECT-TYPE
		SYNTAX 			DisplayString
		MAX-ACCESS		write-only
		STATUS			current
		DESCRIPTION 
		"
		Adding bmc user.
		The data format is 'username,password,userGroupName'.
		please enter the group name from the following actual group names.
		Administrator
		Operator
		User
		'OEMGroup1'
		'OEMGroup2'
		'OMEGroup3'
		'OEMGroup4'
		'OEMGroup5'
		"
		::= {bmcUserManagement 2} 
	delBmcUser OBJECT-TYPE
		SYNTAX 			DisplayString
		MAX-ACCESS		write-only
		STATUS			current
		DESCRIPTION 
		"
		Deleting bmc user by user name.
		"
		::= {bmcUserManagement 3} 
	userPasswdComplexity OBJECT-TYPE
		SYNTAX 			Integer32
						{
						disable(0),
						enable(1)
						}
		MAX-ACCESS		read-write
		STATUS			current
		DESCRIPTION 
		"
		user passwd complexity do check or not when user's passwd is being setting.
		"
		::= {bmcUserManagement 4} 
--bmcUserManagement end
--serviceTable start
	serviceTable	OBJECT-TYPE
	    SYNTAX     SEQUENCE OF ServiceEntry
	    MAX-ACCESS not-accessible
	    STATUS     current
	    DESCRIPTION
	    "
	    The table of service information.
	    "
		::= {serverBmcInfo 6}
	serviceEntry OBJECT-TYPE
	    SYNTAX     ServiceEntry
	    MAX-ACCESS not-accessible
	    STATUS     current
	    DESCRIPTION
	           ""
	    INDEX   { 
				  serviceIndex                
	            }
	    ::= { serviceTable 1 }   
	
	ServiceEntry ::= SEQUENCE {
		serviceIndex			Integer32,
		serviceName				DisplayString,
	    serviceStatus			Integer32,
	    serviceInterface		DisplayString,
		serviceSecurePort		Integer32,
		serviceNonSecurePort	Integer32,
		serviceTimeOut			Integer32,
		serviceMaxSession		Integer32
	}
	serviceIndex OBJECT-TYPE
		SYNTAX 			Integer32
		MAX-ACCESS		read-only
		STATUS			current
		DESCRIPTION 
		"
		The index associated with the service of this entry.	
		"
		::= {serviceEntry 1}
	serviceName OBJECT-TYPE
		SYNTAX 			DisplayString
		MAX-ACCESS		read-only
		STATUS			current
		DESCRIPTION 
		"
		The name of the service.	
		"
		::= {serviceEntry 2}
	serviceStatus OBJECT-TYPE
		SYNTAX 			Integer32
						{
						inactive(0),
						active(1)
						}
		MAX-ACCESS		read-write
		STATUS			current
		DESCRIPTION 
		"
		The status associated with the service of this entry.	
		"
		::= {serviceEntry 3}
	serviceInterface OBJECT-TYPE
		SYNTAX 			DisplayString
		MAX-ACCESS		read-write
		STATUS			current
		DESCRIPTION 
		"
		The interface name associated with the service of this entry.	
		"
		::= {serviceEntry 4}
	serviceSecurePort OBJECT-TYPE
		SYNTAX 			Integer32
						{
							NA(-1)
						}
		MAX-ACCESS		read-write
		STATUS			current
		DESCRIPTION 
		"
		The secure port associated with the service of this entry.	
		"
		::= {serviceEntry 5}
	serviceNonSecurePort OBJECT-TYPE
		SYNTAX 			Integer32
						{
							NA(-1)
						}
		MAX-ACCESS		read-write
		STATUS			current
		DESCRIPTION 
		"
		The no secure port associated with the service of this entry.	
		"
		::= {serviceEntry 6}
	serviceTimeOut OBJECT-TYPE
		SYNTAX 			Integer32
						{
							NA(-1)
						}
		MAX-ACCESS		read-write
		STATUS			current
		DESCRIPTION 
		"
		The time out with the service of this entry.	
		"
		::= {serviceEntry 7}
	serviceMaxSession OBJECT-TYPE
		SYNTAX 			Integer32
						{
							NA(-1)
						}
		MAX-ACCESS		read-only
		STATUS			current
		DESCRIPTION 
		"
		The max session count associated with the service of this entry.	
		"
		::= {serviceEntry 8}
--serviceTable end
--networkLinkTable start
--	networkLinkTable	OBJECT-TYPE
--	    SYNTAX     SEQUENCE OF networkLinkEntry
--	    MAX-ACCESS not-accessible
--	    STATUS     current
--	    DESCRIPTION
--	    "
--	    The table of service information.
--	    "
--		::= {serverBmcInfo 7}
--	networkLinkEntry OBJECT-TYPE
--	    SYNTAX     networkLinkEntry
--	    MAX-ACCESS not-accessible
--	    STATUS     current
--	    DESCRIPTION
--	           ""
--	    INDEX   { 
--				  networkLinkIndex                
--	            }
--	    ::= { networkLinkTable 1 }   
--	
--	networkLinkEntry ::= SEQUENCE {
--		networkLinkIndex		Integer32,
--		interfaceName			DisplayString,
--	    negotiationMode			Integer32,
--	    networkLinkSpeed		DisplayString,
--		networkLinkDuplexMode	Integer32
--	}
--	networkLinkIndex OBJECT-TYPE
--		SYNTAX 			Integer32
--		MAX-ACCESS		read-only
--		STATUS			current
--		DESCRIPTION 
--		"
--		The index associated with the network link of this entry.	
--		"
--		::= {networkLinkEntry 1}
--	interfaceName OBJECT-TYPE
--		SYNTAX 			DisplayString
--		MAX-ACCESS		read-only
--		STATUS			current
--		DESCRIPTION 
--		"
--		The interface name of the network.	
--		"
--		::= {networkLinkEntry 2}
--	negotiationMode OBJECT-TYPE
--		SYNTAX 			Integer32
--						{
--						manual(0),
--						auto(1)
--						}
--		MAX-ACCESS		read-write
--		STATUS			current
--		DESCRIPTION 
--		"
--		The negotiation mode associated with the network link of this entry.	
--		"
--		::= {networkLinkEntry 3}
--	networkLinkSpeed OBJECT-TYPE
--		SYNTAX 			DisplayString
--		MAX-ACCESS		read-write
--		STATUS			current
--		DESCRIPTION 
--		"
--		The speed associated with the network link of this entry.	
--		in auto mode, the speed is 1000 Mbps.
--		in manual mode, you can set the speed with 100 Mbps or 10 Mbps.
--		"
--		::= {networkLinkEntry 4}
--	networkLinkDuplexMode OBJECT-TYPE
--		SYNTAX 			Integer32
--						{
--							HalfDuplex(0),
--							FullDuplex(1)
--						}
--		MAX-ACCESS		read-write
--		STATUS			current
--		DESCRIPTION 
--		"
--		The duplex mode associated with the network link of this entry.	
--		"
--		::= {networkLinkEntry 5}
--networkLinkTable end
--remoteSessionConf start
	kvmSinglePortStatus OBJECT-TYPE
		SYNTAX			Integer32
						{
							disable(0),
							enable(1)
						}
		MAX-ACCESS		read-only
		STATUS			current
		DESCRIPTION
		"
		"
		::= {remoteSessionConf 1}
--	kvmEncryptionStatus OBJECT-TYPE
--		SYNTAX			Integer32
--						{
--							disable(0),
--							disable(0),
--							enable(1)
--						}
--		MAX-ACCESS		read-write
--		STATUS			current
--		DESCRIPTION
--		"
--		"
--		::= {remoteSessionConf 1}
	keyBoardLanguage OBJECT-TYPE
		SYNTAX			Integer32
						{
							Auto-Detect(0),
							English-UK(1),
							English-US(2),
							German(3),
							Japanese(4)	
						}
		MAX-ACCESS		read-write
		STATUS			current
		DESCRIPTION
		"
			you can set it between 0 and 4
		"
		::= {remoteSessionConf 2}
	retryCount OBJECT-TYPE
		SYNTAX			Integer32
		MAX-ACCESS		read-write
		STATUS			current
		DESCRIPTION
		"
		"
		::= {remoteSessionConf 3}
	retryTimeInterval OBJECT-TYPE
		SYNTAX			Integer32
		MAX-ACCESS		read-write
		STATUS			current
		DESCRIPTION
		"
		"
		::= {remoteSessionConf 4}
	serverMonitorOff OBJECT-TYPE
		SYNTAX			Integer32
						{
							disable(0),
							enable(1)
						}
		MAX-ACCESS		read-write
		STATUS			current
		DESCRIPTION
		"
		"
		::= {remoteSessionConf 5}
	automaticOff OBJECT-TYPE
		SYNTAX			Integer32
						{
							disable(0),
							enable(1)
						}
		MAX-ACCESS		read-write
		STATUS			current
		DESCRIPTION
		"
		"
		::= {remoteSessionConf 6}
--remoteSessionConf end
--vmediaInstanceConf start
	cdInstances OBJECT-TYPE
		SYNTAX			Integer32
		MAX-ACCESS		read-write
		STATUS			current
		DESCRIPTION
		"
		"
		::= {vmediaInstanceConf 1}
	hdInstances OBJECT-TYPE
		SYNTAX			Integer32
		MAX-ACCESS		read-write
		STATUS			current
		DESCRIPTION
		"
		"
		::= {vmediaInstanceConf 2}
	remoteCDInstances OBJECT-TYPE
		SYNTAX			Integer32
		MAX-ACCESS		read-write
		STATUS			current
		DESCRIPTION
		"
		"
		::= {vmediaInstanceConf 3}
	remoteHDInstances OBJECT-TYPE
		SYNTAX			Integer32
		MAX-ACCESS		read-write
		STATUS			current
		DESCRIPTION
		"
		"
		::= {vmediaInstanceConf 4}
--	EncryptMedia OBJECT-TYPE
--		SYNTAX			Integer32
--						{
--						disable(0),
--						enable(1)
--						}
--		MAX-ACCESS		read-write
--		STATUS			current
--		DESCRIPTION
--		"
--		"
--		::= {vmediaInstanceConf 5}
	sdMediaEnable OBJECT-TYPE
		SYNTAX			Integer32
						{
						disable(0),
						enable(1)
						}
		MAX-ACCESS		read-write
		STATUS			current
		DESCRIPTION
		"
		"
		::= {vmediaInstanceConf 5}
	powerSaveMode OBJECT-TYPE
		SYNTAX			Integer32
						{
						disable(0),
						enable(1)
						}
		MAX-ACCESS		read-write
		STATUS			current
		DESCRIPTION
		"
		"
		::= {vmediaInstanceConf 6}
--	sdMediaEnable OBJECT-TYPE
--		SYNTAX			Integer32
--						{
--						disable(0),
--						enable(1)
--						}
--		MAX-ACCESS		read-write
--		STATUS			current
--		DESCRIPTION
--		"
--		"
--		::= {vmediaInstanceConf 6}
--vmediaInstanceConf end
--generalRADIUSConf start
	radiusAuth OBJECT-TYPE
		SYNTAX			Integer32
						{
						disable(0),
						enable(1)
						}
		MAX-ACCESS		read-write
		STATUS			current
		DESCRIPTION
		"
		"
		::= {generalRADIUSConf 1}
	serverAddress OBJECT-TYPE
		SYNTAX			DisplayString
		MAX-ACCESS		read-write
		STATUS			current
		DESCRIPTION
		"
		"
		::= {generalRADIUSConf 2}
	authPort OBJECT-TYPE
		SYNTAX			Integer32 (1..65535)
		MAX-ACCESS		read-write
		STATUS			current
		DESCRIPTION
		"
		"
		::= {generalRADIUSConf 3}
	authSecret OBJECT-TYPE
		SYNTAX			DisplayString
		MAX-ACCESS		read-write
		STATUS			current
		DESCRIPTION
		"
		"
		::= {generalRADIUSConf 4}
--generalRADIUSConf end
--bmcDNSConf start
	bmcDNSEnable  OBJECT-TYPE
		SYNTAX 			Integer32{
						disable(0),
						enable(1)
		} 
		MAX-ACCESS		read-write
		STATUS			current
		DESCRIPTION 
		"
		The DNS enable of the BMC network interface DNS configuration.	
		"
		::= {bmcDNSConf 1}  
	bmcmDNSEnable  OBJECT-TYPE
		SYNTAX 			Integer32{
						disable(0),
						enable(1)
		} 
		MAX-ACCESS		read-write
		STATUS			current
		DESCRIPTION 
		"
		The multicast DNS enable of the BMC network interface DNS configuration.	
		"
		::= {bmcDNSConf 2}  
	bmcDNSHostMode  OBJECT-TYPE
		SYNTAX 			Integer32{
						manual(0),
						automatic(1)
		} 
		MAX-ACCESS		read-write
		STATUS			current
		DESCRIPTION 
		"
		The host setting of the BMC network interface DNS configuration.	
		"
		::= {bmcDNSConf 3}  
	bmcDNSHostName  OBJECT-TYPE
		SYNTAX 			DisplayString 
		MAX-ACCESS		read-write
		STATUS			current
		DESCRIPTION 
		"
		The host name of the BMC network interface DNS configuration.	
		"
		::= {bmcDNSConf 4} 
    
 	bmcDNSRegisterEth0Enable  OBJECT-TYPE
		SYNTAX 			Integer32{
						disable(0),
						enable(1)
		} 
		MAX-ACCESS		read-write
		STATUS			current
		DESCRIPTION 
		"
		The DNS eth0 enable of the BMC network interface DNS register.	
		"
		::= {bmcDNSConf 5}  
     bmcDNSRegisterEth0Method  OBJECT-TYPE
		SYNTAX 			Integer32{
						nsUpdate (0),
						dhcpClientFQDN (1),
						hostName(2),
						none(3)
		} 
		MAX-ACCESS		read-write
		STATUS			current
		DESCRIPTION 
		"
		The DNS eth0 configuration of the BMC network interface DNS register.	
		"
		::= {bmcDNSConf 6}
	bmcDNSRegisterEth1Enable  OBJECT-TYPE
		SYNTAX 			Integer32{
						disable(0),
						enable(1)
		} 
		MAX-ACCESS		read-write
		STATUS			current
		DESCRIPTION 
		"
		The DNS eth1 enable of the BMC network interface DNS register.	
		"
		::= {bmcDNSConf 7}  
     bmcDNSRegisterEth1Method  OBJECT-TYPE
		SYNTAX 			Integer32{
						nsUpdate (0),
						dhcpClientFQDN (1),
						hostName(2),
						none(3)
		} 
		MAX-ACCESS		read-write
		STATUS			current
		DESCRIPTION 
		"
		The DNS eth1 configuration of the BMC network interface DNS register.	
		"
		::= {bmcDNSConf 8}   
	bmcDNSDomainNetworkMode  OBJECT-TYPE
		SYNTAX 			Integer32{
						manual (0),
						automatic (1)
		} 
		MAX-ACCESS		read-write
		STATUS			current
		DESCRIPTION 
		"
		The DNS domain network mode of the BMC network interface DNS domain configuration.	
		"
		::= {bmcDNSConf 9}		
	bmcDNSDomainNetworkInterface  OBJECT-TYPE
		SYNTAX 			Integer32{
						eth0-v4 (0),  
						eth0-v6 (1), 
						eth1-v4 (2),  
						eth1-v6 (3)
		} 
		MAX-ACCESS		read-write
		STATUS			current
		DESCRIPTION 
		"
		The DNS domain network interface of the BMC network interface DNS domain configuration.	
		If eth1 is in static mode ,you cann't set 2.
		"
		::= {bmcDNSConf 10}      
	bmcDNSDomainName  OBJECT-TYPE
		SYNTAX 			DisplayString 
		MAX-ACCESS		read-write
		STATUS			current
		DESCRIPTION 
		"
		The DNS domain name of the BMC network interface DNS domain configuration.	
		"
		::= {bmcDNSConf 11}
	bmcDNSDomainServerMode  OBJECT-TYPE
		SYNTAX 			Integer32{
						manual (0),
						automatic (1)
		} 
		MAX-ACCESS		read-write
		STATUS			current
		DESCRIPTION 
		"
		The DNS domain server mode of the BMC network interface DNS server configuration.	
		"
		::= {bmcDNSConf 12}  
	bmcDNSDomainServerInterface  OBJECT-TYPE
		SYNTAX 			DisplayString
		MAX-ACCESS		read-only
		STATUS			current
		DESCRIPTION 
		"
		The DNS server interface of the BMC network interface DNS server configuration.	
		"
		::= {bmcDNSConf 13}  
	bmcDNSDomainServerIPPriority  OBJECT-TYPE
		SYNTAX 			Integer32{
						na(0),
						ipv4 (1),
						ipv6 (2)
		} 
		MAX-ACCESS		read-write
		STATUS			current
		DESCRIPTION 
		"
		The DNS server IP priority of the BMC network interface DNS server configuration.	
		"
		::= {bmcDNSConf 14}
	bmcDNSDomainServerIPaddr1  OBJECT-TYPE
		SYNTAX 			DisplayString 
		MAX-ACCESS		read-write
		STATUS			current
		DESCRIPTION 
		"
		The DNS server IP address 1 of the BMC network interface DNS server configuration.	
		"
		::= {bmcDNSConf 15}
	bmcDNSDomainServerIPaddr2  OBJECT-TYPE
		SYNTAX 			DisplayString 
		MAX-ACCESS		read-write
		STATUS			current
		DESCRIPTION 
		"
		The DNS server IP address 2 of the BMC network interface DNS server configuration.	
		"
		::= {bmcDNSConf 16} 
	bmcDNSDomainServerIPaddr3  OBJECT-TYPE
		SYNTAX 			DisplayString 
		MAX-ACCESS		read-write
		STATUS			current
		DESCRIPTION 
		"
		The DNS server IP address 3 of the BMC network interface DNS server configuration.	
		"
		::= {bmcDNSConf 17}	
--bmcDNSConf end
--kvmMouseSetting start
--	kvmMouseMode  OBJECT-TYPE
--		SYNTAX 			Integer32
--						{
--							relative(1),
--							absolute(2),
--							otherMode(3)
--						}
--		MAX-ACCESS		read-only
--		STATUS			current
--		DESCRIPTION 
--		"
--		The kvm mouse mode.	
--		"
--		::= {kvmMouseSetting 1} 
--	kvmMouseModeControl  OBJECT-TYPE
--		SYNTAX 			Integer32
--						{
--							relative(1),
--							absolute(2),
--							otherMode(3)
--						}
--		MAX-ACCESS		write-only
--		STATUS			current
--		DESCRIPTION 
--		"
--		Set the kvm mouse mode.	
--		1 for relative positioning
--		2 for absolute positioning
--		3 for other mode
--		"
--		::= {kvmMouseSetting 2}	
--kvmMouseSetting end
--sslCertMessage start
	certificateVersion  OBJECT-TYPE
		SYNTAX 			Integer32
		MAX-ACCESS		read-only
		STATUS			current
		DESCRIPTION 
		"
		"
		::= {sslCertMessage 1} 
	serialNumber  OBJECT-TYPE
		SYNTAX 			DisplayString
		MAX-ACCESS		read-only
		STATUS			current
		DESCRIPTION 
		"
		"
		::= {sslCertMessage 2} 
	signatureAlgorithm  OBJECT-TYPE
		SYNTAX 			DisplayString
		MAX-ACCESS		read-only
		STATUS			current
		DESCRIPTION 
		"
		"
		::= {sslCertMessage 3} 
	publicKey  OBJECT-TYPE
		SYNTAX 			DisplayString
		MAX-ACCESS		read-only
		STATUS			current
		DESCRIPTION 
		"
		"
		::= {sslCertMessage 4} 
	issuerCommonName  OBJECT-TYPE
		SYNTAX 			DisplayString
		MAX-ACCESS		read-only
		STATUS			current
		DESCRIPTION 
		"
		"
		::= {sslCertMessage 5} 
	issuerOrganization  OBJECT-TYPE
		SYNTAX 			DisplayString
		MAX-ACCESS		read-only
		STATUS			current
		DESCRIPTION 
		"
		"
		::= {sslCertMessage 6} 
	issuerOrganizationUnit  OBJECT-TYPE
		SYNTAX 			DisplayString
		MAX-ACCESS		read-only
		STATUS			current
		DESCRIPTION 
		"
		"
		::= {sslCertMessage 7} 
	issuerCityLocality  OBJECT-TYPE
		SYNTAX 			DisplayString
		MAX-ACCESS		read-only
		STATUS			current
		DESCRIPTION 
		"
		"
		::= {sslCertMessage 8} 
	issuerStateProvince  OBJECT-TYPE
		SYNTAX 			DisplayString
		MAX-ACCESS		read-only
		STATUS			current
		DESCRIPTION 
		"
		"
		::= {sslCertMessage 9} 
	issuerCountry  OBJECT-TYPE
		SYNTAX 			DisplayString
		MAX-ACCESS		read-only
		STATUS			current
		DESCRIPTION 
		"
		"
		::= {sslCertMessage 10} 
	issuerEmailAddress  OBJECT-TYPE
		SYNTAX 			DisplayString
		MAX-ACCESS		read-only
		STATUS			current
		DESCRIPTION 
		"
		"
		::= {sslCertMessage 11} 
	validFrom  OBJECT-TYPE
		SYNTAX 			DisplayString
		MAX-ACCESS		read-only
		STATUS			current
		DESCRIPTION 
		"
		"
		::= {sslCertMessage 12} 
	validTill  OBJECT-TYPE
		SYNTAX 			DisplayString
		MAX-ACCESS		read-only
		STATUS			current
		DESCRIPTION 
		"
		"
		::= {sslCertMessage 13} 
	issuedToCommonName  OBJECT-TYPE
		SYNTAX 			DisplayString
		MAX-ACCESS		read-only
		STATUS			current
		DESCRIPTION 
		"
		"
		::= {sslCertMessage 14} 
	issuedToOrganization  OBJECT-TYPE
		SYNTAX 			DisplayString
		MAX-ACCESS		read-only
		STATUS			current
		DESCRIPTION 
		"
		"
		::= {sslCertMessage 15} 
	issuerToOrganizationUnit  OBJECT-TYPE
		SYNTAX 			DisplayString
		MAX-ACCESS		read-only
		STATUS			current
		DESCRIPTION 
		"
		"
		::= {sslCertMessage 16} 
	issuerToCityLocality  OBJECT-TYPE
		SYNTAX 			DisplayString
		MAX-ACCESS		read-only
		STATUS			current
		DESCRIPTION 
		"
		"
		::= {sslCertMessage 17} 
	issuerToStateProvince  OBJECT-TYPE
		SYNTAX 			DisplayString
		MAX-ACCESS		read-only
		STATUS			current
		DESCRIPTION 
		"
		"
		::= {sslCertMessage 18} 
	issuerToCountry  OBJECT-TYPE
		SYNTAX 			DisplayString
		MAX-ACCESS		read-only
		STATUS			current
		DESCRIPTION 
		"
		"
		::= {sslCertMessage 19} 
	issuerToEmailAddress  OBJECT-TYPE
		SYNTAX 			DisplayString
		MAX-ACCESS		read-only
		STATUS			current
		DESCRIPTION 
		"
		"
		::= {sslCertMessage 20}  
--sslCertMessage end
--snmptrapPoliciesTable start	
	snmptrapPoliciesTable	OBJECT-TYPE
	    SYNTAX     SEQUENCE OF SnmptrapPoliciesEntry
	    MAX-ACCESS not-accessible
	    STATUS     current
	    DESCRIPTION
	    "
	    The table of snmp trap policy.
	    "
		::= {alarmSetting 1}
	snmptrapPoliciesEntry OBJECT-TYPE
	    SYNTAX     SnmptrapPoliciesEntry
	    MAX-ACCESS not-accessible
	    STATUS     current
	    DESCRIPTION
	           ""
	    INDEX   { 
				  snmptrapIndex                
	            }
	    ::= { snmptrapPoliciesTable 1 }   
	
	SnmptrapPoliciesEntry ::= SEQUENCE {
		snmptrapIndex			Integer32,
		snmptrapEnable			Integer32,
	    snmptrapVersion			Integer32,
	    snmptrapSeverity		Integer32,
		snmptrapPort			Integer32,
		snmptrapName			DisplayString,
		snmptrapCommunity		DisplayString,
		snmptrapEnginedId		DisplayString,
		snmptrapAlertEnable1		Integer32,
		snmptrapSnmpAddr1		DisplayString,
		snmptrapAlertEnable2		Integer32,
		snmptrapSnmpAddr2		DisplayString,
		snmptrapAlertEnable3		Integer32,
		snmptrapSnmpAddr3		DisplayString,
		snmptrapAlertEnable4		Integer32,
		snmptrapSnmpAddr4		DisplayString
		
	}
	snmptrapIndex OBJECT-TYPE
		SYNTAX 			Integer32
		MAX-ACCESS		read-only
		STATUS			current
		DESCRIPTION 
		"
		The index associated with the snmptrap of this entry.	
		"
		::= {snmptrapPoliciesEntry 1}
	snmptrapEnable OBJECT-TYPE
		SYNTAX 			Integer32
						{
							diabled(0),
							enable(1)
						}
		MAX-ACCESS		read-write
		STATUS			current
		DESCRIPTION 
		"
		The trap enable associated with the snmptrap of this entry.	
		"
		::= {snmptrapPoliciesEntry 2}
	snmptrapVersion OBJECT-TYPE
		SYNTAX 			Integer32
						{
							V1(1),
							V2(2),
							V3(3)
						}
		MAX-ACCESS		read-write
		STATUS			current
		DESCRIPTION 
		"
		The trap version associated with the snmptrap of this entry.	
		"
		::= {snmptrapPoliciesEntry 3}
	snmptrapSeverity OBJECT-TYPE
		SYNTAX 			Integer32
						{
							info(1),
							waring(2),
							critical(3)
						}
		MAX-ACCESS		read-write
		STATUS			current
		DESCRIPTION 
		"
		The trap severity associated with the snmptrap of this entry.	
		"
		::= {snmptrapPoliciesEntry 4}
	snmptrapPort OBJECT-TYPE
		SYNTAX 			Integer32
		MAX-ACCESS		read-write
		STATUS			current
		DESCRIPTION 
		"
		The trap port associated with the snmptrap of this entry.	
		"
		::= {snmptrapPoliciesEntry 5}
	snmptrapName OBJECT-TYPE
		SYNTAX 			DisplayString
		MAX-ACCESS		read-write
		STATUS			current
		DESCRIPTION 
		"
		The trap name associated with the snmptrap of this entry.	
							
		"
		::= {snmptrapPoliciesEntry 6}
	snmptrapCommunity OBJECT-TYPE
		SYNTAX 			DisplayString
		MAX-ACCESS		read-write
		STATUS			current
		DESCRIPTION 
		"
		The trap community associated with the snmptrap of this entry.							
		"
		::= {snmptrapPoliciesEntry 7} 
	snmptrapEnginedId OBJECT-TYPE
		SYNTAX 			DisplayString
		MAX-ACCESS		read-write
		STATUS			current
		DESCRIPTION 
		"
		The engined id associated with the snmptrap of this entry.					
		"
		::= {snmptrapPoliciesEntry 8}
	snmptrapAlertEnable1 OBJECT-TYPE
		SYNTAX 			Integer32
						{
							diabled(0),
							enable(1)
						}
		MAX-ACCESS		read-write
		STATUS			current
		DESCRIPTION 
		"
		The trap Alert 1 enable associated with the snmptrap of this entry.	
		"
		::= {snmptrapPoliciesEntry 9}
	snmptrapSnmpAddr1 OBJECT-TYPE
		SYNTAX 			DisplayString
		MAX-ACCESS		read-write
		STATUS			current
		DESCRIPTION 
		"
		The trap Alert 1 addr associated with the snmptrap of this entry.								
		"
		::= {snmptrapPoliciesEntry 10}
	snmptrapAlertEnable2 OBJECT-TYPE
		SYNTAX 			Integer32
						{
							diabled(0),
							enable(1)
						}
		MAX-ACCESS		read-write
		STATUS			current
		DESCRIPTION 
		"
		The trap Alert 2 enable associated with the snmptrap of this entry.		
		"
		::= {snmptrapPoliciesEntry 11}
	snmptrapSnmpAddr2 OBJECT-TYPE
		SYNTAX 			DisplayString
		MAX-ACCESS		read-write
		STATUS			current
		DESCRIPTION 
		"
		The trap Alert 2 addr associated with the snmptrap of this entry.							
		"
		::= {snmptrapPoliciesEntry 12}
	snmptrapAlertEnable3 OBJECT-TYPE
		SYNTAX 			Integer32
						{
							diabled(0),
							enable(1)
						}
		MAX-ACCESS		read-write
		STATUS			current
		DESCRIPTION 
		"
		The trap Alert 3 enable associated with the snmptrap of this entry.	
		"
		::= {snmptrapPoliciesEntry 13}
	snmptrapSnmpAddr3 OBJECT-TYPE
		SYNTAX 			DisplayString
		MAX-ACCESS		read-write
		STATUS			current
		DESCRIPTION 
		"
		The trap Alert 3 addr associated with the snmptrap of this entry.							
		"
		::= {snmptrapPoliciesEntry 14}
	snmptrapAlertEnable4 OBJECT-TYPE
		SYNTAX 			Integer32
						{
							diabled(0),
							enable(1)
						}
		MAX-ACCESS		read-write
		STATUS			current
		DESCRIPTION 
		"
		The trap Alert 4 enable associated with the snmptrap of this entry.		
		"
		::= {snmptrapPoliciesEntry 15}
	snmptrapSnmpAddr4 OBJECT-TYPE
		SYNTAX 			DisplayString
		MAX-ACCESS		read-write
		STATUS			current
		DESCRIPTION 
		"
		The trap Alert 4 addr associated with the snmptrap of this entry.							
		"
		::= {snmptrapPoliciesEntry 16} 		
--snmptrapPoliciesTable end
--emailalarmPoliciesTable start	
	emailalarmPoliciesTable	OBJECT-TYPE
	    SYNTAX     SEQUENCE OF EmailalarmPoliciesEntry
	    MAX-ACCESS not-accessible
	    STATUS     current
	    DESCRIPTION
	    "
	    The table of eamil alarm policy.
	    "
		::= {alarmSetting 2}
	emailalarmPoliciesEntry OBJECT-TYPE
	    SYNTAX     EmailalarmPoliciesEntry
	    MAX-ACCESS not-accessible
	    STATUS     current
	    DESCRIPTION
	           ""
	    INDEX   { 
				  emailalarmIndex                
	            }
	    ::= { emailalarmPoliciesTable 1 }   
	
	EmailalarmPoliciesEntry ::= SEQUENCE {
		emailalarmIndex				Integer32,
		emailalarmEnable			Integer32,
	    emailalarmSeverity			Integer32,
		emailalarmSubject			DisplayString,
		emailalarmAlertEnable1		Integer32,
		emailalarmUserName1			DisplayString,
		emailalarmMessage1			DisplayString,
		emailalarmAlertEnable2		Integer32,
		emailalarmUserName2			DisplayString,
		emailalarmMessage2			DisplayString,
		emailalarmAlertEnable3		Integer32,
		emailalarmUserName3			DisplayString,
		emailalarmMessage3			DisplayString,
		emailalarmAlertEnable4		Integer32,
		emailalarmUserName4			DisplayString,
		emailalarmMessage4			DisplayString
		
	}
	emailalarmIndex OBJECT-TYPE
		SYNTAX 			Integer32
		MAX-ACCESS		read-only
		STATUS			current
		DESCRIPTION 
		"
		The index associated with the emailalarm.	
		"
		::= {emailalarmPoliciesEntry 1}
	emailalarmEnable OBJECT-TYPE
		SYNTAX 			Integer32
						{
							diabled(0),
							enable(1)
						}
		MAX-ACCESS		read-write
		STATUS			current
		DESCRIPTION 
		"
		The email alarm enable associated with the emailalarm.	
		"
		::= {emailalarmPoliciesEntry 2}
	emailalarmSeverity OBJECT-TYPE
		SYNTAX 			Integer32
						{
							info(1),
							waring(2),
							critical(3)
						}
		MAX-ACCESS		read-write
		STATUS			current
		DESCRIPTION 
		"
		The email alarm severity associated with the emailalarm .	
		"
		::= {emailalarmPoliciesEntry 3}
	emailalarmSubject OBJECT-TYPE
		SYNTAX 			DisplayString
		MAX-ACCESS		read-write
		STATUS			current
		DESCRIPTION 
		"
		The email alarm subject associated with the emailalarm.	
		"
		::= {emailalarmPoliciesEntry 4}
	emailalarmAlertEnable1 OBJECT-TYPE
		SYNTAX 			Integer32
						{
							diabled(0),
							enable(1)
						}
		MAX-ACCESS		read-write
		STATUS			current
		DESCRIPTION 
		"
		The email alarm alert enable 1 associated with the emailalarm.	
		"
		::= {emailalarmPoliciesEntry 5}
	emailalarmUserName1 OBJECT-TYPE
		SYNTAX 			DisplayString
		MAX-ACCESS		read-write
		STATUS			current
		DESCRIPTION 
		"
		The email alarm username 1 associated with the emailalarm.						
		"
		::= {emailalarmPoliciesEntry 6}
	emailalarmMessage1 OBJECT-TYPE
		SYNTAX 			DisplayString
		MAX-ACCESS		read-write
		STATUS			current
		DESCRIPTION 
		"
		The email alarm message 1 associated with the emailalarm.
		"
		::= {emailalarmPoliciesEntry 7} 
	emailalarmAlertEnable2 OBJECT-TYPE
		SYNTAX 			Integer32
						{
							diabled(0),
							enable(1)
						}
		MAX-ACCESS		read-write
		STATUS			current
		DESCRIPTION 
		"
		The email alarm alert enable 2 associated with the emailalarm.
		"
		::= {emailalarmPoliciesEntry 8}
	emailalarmUserName2 OBJECT-TYPE
		SYNTAX 			DisplayString
		MAX-ACCESS		read-write
		STATUS			current
		DESCRIPTION 
		"
		The email alarm username 2 associated with the emailalarm.
		"
		::= {emailalarmPoliciesEntry 9}
	emailalarmMessage2 OBJECT-TYPE
		SYNTAX 			DisplayString
		MAX-ACCESS		read-write
		STATUS			current
		DESCRIPTION 
		"
		The email alarm message 2 associated with the emailalarm.
		"
		::= {emailalarmPoliciesEntry 10} 
	emailalarmAlertEnable3 OBJECT-TYPE
		SYNTAX 			Integer32
						{
							diabled(0),
							enable(1)
						}
		MAX-ACCESS		read-write
		STATUS			current
		DESCRIPTION 
		"
		The email alarm alert enable 3 associated with the emailalarm.
		"
		::= {emailalarmPoliciesEntry 11}
	emailalarmUserName3 OBJECT-TYPE
		SYNTAX 			DisplayString
		MAX-ACCESS		read-write
		STATUS			current
		DESCRIPTION 
		"
		The email alarm username 3 associated with the emailalarm.
		"
		::= {emailalarmPoliciesEntry 12}
	emailalarmMessage3 OBJECT-TYPE
		SYNTAX 			DisplayString
		MAX-ACCESS		read-write
		STATUS			current
		DESCRIPTION 
		"
		The email alarm message 3 associated with the emailalarm.
		"
		::= {emailalarmPoliciesEntry 13} 
	emailalarmAlertEnable4 OBJECT-TYPE
		SYNTAX 			Integer32
						{
							diabled(0),
							enable(1)
						}
		MAX-ACCESS		read-write
		STATUS			current
		DESCRIPTION 
		"
		The email alarm alert enable 4 associated with the emailalarm.	
		"
		::= {emailalarmPoliciesEntry 14}
	emailalarmUserName4 OBJECT-TYPE
		SYNTAX 			DisplayString
		MAX-ACCESS		read-write
		STATUS			current
		DESCRIPTION 
		"
		The email alarm username 4 associated with the emailalarm.
		"
		::= {emailalarmPoliciesEntry 15}
	emailalarmMessage4 OBJECT-TYPE
		SYNTAX 			DisplayString
		MAX-ACCESS		read-write
		STATUS			current
		DESCRIPTION 
		"
		The email alarm message 4 associated with the emailalarm.
		"
		::= {emailalarmPoliciesEntry 16} 	
--emailalarmPoliciesTable end
--bmcSMTPTable start
	bmcSMTPTable	OBJECT-TYPE
	    SYNTAX     SEQUENCE OF BmcSMTPEntry
	    MAX-ACCESS not-accessible
	    STATUS     current
	    DESCRIPTION
	    "
	    The table of service information.
	    "
		::= {serverBmcInfo 14}
	bmcSMTPEntry OBJECT-TYPE
	    SYNTAX     BmcSMTPEntry
	    MAX-ACCESS not-accessible
	    STATUS     current
	    DESCRIPTION
	           ""
	    INDEX   { 
				  bmcSMTPIndex                
	            }
	    ::= { bmcSMTPTable 1 }   
	
	BmcSMTPEntry ::= SEQUENCE {
		bmcSMTPIndex				Integer32,
--		bmcSMTPLanInterface			DisplayString,
	    bmcSMTPEmailID				DisplayString,
	    bmcSMTPPrimarySupport		Integer32,
		bmcSMTPPrimaryServerName	DisplayString,
		bmcSMTPPrimaryServerIP		DisplayString,
		bmcSMTPPrimaryServerPort	Integer32,
		bmcSMTPPrimarySecurePort	Integer32,
		bmcSMTPPrimaryAuth			Integer32,
		bmcSMTPPrimaryUserName		DisplayString,
		bmcSMTPPrimaryPassword		DisplayString,
		bmcSMTPSecondSupport		Integer32,
		bmcSMTPSecondServerName		DisplayString,
		bmcSMTPSecondServerIP		DisplayString,
		bmcSMTPSecondServerPort		Integer32,
		bmcSMTPSecondSecurePort		Integer32,
		bmcSMTPSecondAuth			Integer32,
		bmcSMTPSecondUserName		DisplayString,
		bmcSMTPSecondPassword		DisplayString
	}
	bmcSMTPIndex OBJECT-TYPE
		SYNTAX 			Integer32
		MAX-ACCESS		read-only
		STATUS			current
		DESCRIPTION 
		"
		The index associated with the smtp of this entry.	
		"
		::= {bmcSMTPEntry 1}
--	bmcSMTPLanInterface OBJECT-TYPE
--		SYNTAX 			DisplayString
--		MAX-ACCESS		read-only
--		STATUS			current
--		DESCRIPTION 
--		"
--		The lan interface of the smtp.							
--		"
--		::= {bmcSMTPEntry 2} 
	bmcSMTPEmailID OBJECT-TYPE
		SYNTAX 			DisplayString
		MAX-ACCESS		read-write
		STATUS			current
		DESCRIPTION 
		"
		The email id of the smtp.							
		"
		::= {bmcSMTPEntry 2} 
	bmcSMTPPrimarySupport OBJECT-TYPE
		SYNTAX 			Integer32{
						diabled(0),
						enable(1)
						}
		MAX-ACCESS		read-write
		STATUS			current
		DESCRIPTION 
		"
		Enable smtp primary server.							
		"
		::= {bmcSMTPEntry 3} 
	bmcSMTPPrimaryServerName OBJECT-TYPE
		SYNTAX 			DisplayString
		MAX-ACCESS		read-write
		STATUS			current
		DESCRIPTION 
		"
		The name of the smtp primary server.							
		"
		::= {bmcSMTPEntry 4} 
	bmcSMTPPrimaryServerIP OBJECT-TYPE
		SYNTAX 			DisplayString
		MAX-ACCESS		read-write
		STATUS			current
		DESCRIPTION 
		"
		The ip of the smtp primary server.							
		"
		::= {bmcSMTPEntry 5} 
	bmcSMTPPrimaryServerPort OBJECT-TYPE
		SYNTAX 			Integer32
		MAX-ACCESS		read-write
		STATUS			current
		DESCRIPTION 
		"
		The port of the smtp primary server.							
		"
		::= {bmcSMTPEntry 6} 
	bmcSMTPPrimarySecurePort OBJECT-TYPE
		SYNTAX 			Integer32
		MAX-ACCESS		read-only
		STATUS			current
		DESCRIPTION 
		"
		The secure port of the smtp primary server.							
		"
		::= {bmcSMTPEntry 7} 
	bmcSMTPPrimaryAuth OBJECT-TYPE
		SYNTAX 			Integer32{
						diabled(0),
						enable(1)
						}
		MAX-ACCESS		read-write
		STATUS			current
		DESCRIPTION 
		"
		Enable smtp primary server authentication.							
		"
		::= {bmcSMTPEntry 8} 
	bmcSMTPPrimaryUserName OBJECT-TYPE
		SYNTAX 			DisplayString
		MAX-ACCESS		read-write
		STATUS			current
		DESCRIPTION 
		"
		The user name of the smtp primary server.							
		"
		::= {bmcSMTPEntry 9} 
	bmcSMTPPrimaryPassword OBJECT-TYPE
		SYNTAX 			DisplayString
		MAX-ACCESS		read-write
		STATUS			current
		DESCRIPTION 
		"
		The password of the smtp primary server.							
		"
		::= {bmcSMTPEntry 10} 
	bmcSMTPSecondSupport OBJECT-TYPE
		SYNTAX 			Integer32{
						diabled(0),
						enable(1)
						}
		MAX-ACCESS		read-write
		STATUS			current
		DESCRIPTION 
		"
		Enable smtp primary server.							
		"
		::= {bmcSMTPEntry 11} 
	bmcSMTPSecondServerName OBJECT-TYPE
		SYNTAX 			DisplayString
		MAX-ACCESS		read-write
		STATUS			current
		DESCRIPTION 
		"
		The name of the smtp second server.							
		"
		::= {bmcSMTPEntry 12} 
	bmcSMTPSecondServerIP OBJECT-TYPE
		SYNTAX 			DisplayString
		MAX-ACCESS		read-write
		STATUS			current
		DESCRIPTION 
		"
		The ip of the smtp second server.							
		"
		::= {bmcSMTPEntry 13} 
	bmcSMTPSecondServerPort OBJECT-TYPE
		SYNTAX 			Integer32
		MAX-ACCESS		read-write
		STATUS			current
		DESCRIPTION 
		"
		The port of the smtp second server.							
		"
		::= {bmcSMTPEntry 14} 
	bmcSMTPSecondSecurePort OBJECT-TYPE
		SYNTAX 			Integer32
		MAX-ACCESS		read-only
		STATUS			current
		DESCRIPTION 
		"
		The secure port of the smtp second server.							
		"
		::= {bmcSMTPEntry 15} 
	bmcSMTPSecondAuth OBJECT-TYPE
		SYNTAX 			Integer32{
						diabled(0),
						enable(1)
						}
		MAX-ACCESS		read-write
		STATUS			current
		DESCRIPTION 
		"
		Enable smtp second server authentication.							
		"
		::= {bmcSMTPEntry 16} 
	bmcSMTPSecondUserName OBJECT-TYPE
		SYNTAX 			DisplayString
		MAX-ACCESS		read-write
		STATUS			current
		DESCRIPTION 
		"
		The user name of the smtp second server.							
		"
		::= {bmcSMTPEntry 17} 
	bmcSMTPSecondPassword OBJECT-TYPE
		SYNTAX 			DisplayString
		MAX-ACCESS		read-write
		STATUS			current
		DESCRIPTION 
		"
		The password of the smtp second server.							
		"
		::= {bmcSMTPEntry 18} 
--bmcSMTPTable end
--bmcDedicatedDestinationTable start
--	bmcDedicatedDestinationTable	OBJECT-TYPE
--	    SYNTAX     SEQUENCE OF bmcDedicatedDestinationEntry
--	    MAX-ACCESS not-accessible
--	    STATUS     current
--	    DESCRIPTION
--	    "
--	    The table of service information.
--	    "
--		::= {platformEventFilters 3}
--	bmcDedicatedDestinationEntry OBJECT-TYPE
--	    SYNTAX     bmcDedicatedDestinationEntry
--	    MAX-ACCESS not-accessible
--	    STATUS     current
--	    DESCRIPTION
--	           ""
--	    INDEX   { 
--				  bmcDedicatedDestinationIndex                
--	            }
--	    ::= { bmcDedicatedDestinationTable 1 }   
--	
--	bmcDedicatedDestinationEntry ::= SEQUENCE {
--		bmcDedicatedDestinationIndex			Integer32,
--		bmcDedicatedDestinationID				Integer32,
--		bmcDedicatedDestinationType				Integer32,
--		bmcDedicatedDestinationTypeVersion		Integer32,
--	    bmcDedicatedDestinationAddress			DisplayString,
--		bmcDedicatedDestinationTypePort			Integer32,
--		bmcDedicatedDestinationTrapUserName		DisplayString,
--		bmcDedicatedDestinationTrapCommunity	DisplayString,
--	    bmcDedicatedDestinationUserName			DisplayString,
--		bmcDedicatedDestinationEmailSubject		DisplayString,
--		bmcDedicatedDestinationEmailMessage		DisplayString,
--		bmcDedicatedDestinationAuthPro			Integer32,
--		bmcDedicatedDestinationPrivPro		Integer32,
--		bmcDedicatedDestinationAuthPwd		DisplayString,
--		bmcDedicatedDestinationPrivPwd		DisplayString,
--		bmcDedicatedDestinationEngineId		DisplayString
--	}
--	bmcDedicatedDestinationIndex OBJECT-TYPE
--		SYNTAX 			Integer32
--		MAX-ACCESS		read-only
--		STATUS			current
--		DESCRIPTION 
--		"
--		The index associated with the dedicated destination of this entry.	
--		"
--		::= {bmcDedicatedDestinationEntry 1}
--	bmcDedicatedDestinationID OBJECT-TYPE
--		SYNTAX 			Integer32
--		MAX-ACCESS		read-only
--		STATUS			current
--		DESCRIPTION 
--		"
--		The id of the dedicated destination.							
--		"
--		::= {bmcDedicatedDestinationEntry 2} 
--	bmcDedicatedDestinationType OBJECT-TYPE
--		SYNTAX 			Integer32{
--						snmp-trap(1),
--						e-mail(2)
--						}
--		MAX-ACCESS		read-write
--		STATUS			current
--		DESCRIPTION 
--		"
--		The type of the dedicated destination.							
--		"
--		::= {bmcDedicatedDestinationEntry 3} 
--	bmcDedicatedDestinationTypeVersion OBJECT-TYPE
--		SYNTAX 			Integer32{
--						none(0),
--						v1(1),
--						v2c(2),
--						v3(3)
--						}
--		MAX-ACCESS		read-write
--		STATUS			current
--		DESCRIPTION 
--		"
--		The mode of the dedicated destination.							
--		"
--		::= {bmcDedicatedDestinationEntry 4}
--	bmcDedicatedDestinationAddress OBJECT-TYPE
--		SYNTAX 			DisplayString
--		MAX-ACCESS		read-write
--		STATUS			current
--		DESCRIPTION 
--		"
--		The ip address of the dedicated destination.							
--		"
--		::= {bmcDedicatedDestinationEntry 5}	
--	bmcDedicatedDestinationTypePort OBJECT-TYPE
--		SYNTAX 			Integer32
--		MAX-ACCESS		read-write
--		STATUS			current
--		DESCRIPTION 
--		"
--		The port of the dedicated destination.							
--		'bmcDedicatedDestinationTypeVersion' must be setted
--		"
--		::= {bmcDedicatedDestinationEntry 6}
--	bmcDedicatedDestinationTrapUserName OBJECT-TYPE
--		SYNTAX 			DisplayString
--		MAX-ACCESS		read-write
--		STATUS			current
--		DESCRIPTION 
--		"
--		The Trap UserName of the dedicated destination.  
--		'bmcDedicatedDestinationTypeVersion' must be setted
--		"
--		::= {bmcDedicatedDestinationEntry 7}
--	bmcDedicatedDestinationTrapCommunity OBJECT-TYPE
--		SYNTAX 			DisplayString
--		MAX-ACCESS		read-write
--		STATUS			current
--		DESCRIPTION 
--		"
--		The Trap Community of the dedicated destination.							
--		"
--		::= {bmcDedicatedDestinationEntry 8}
--	bmcDedicatedDestinationUserName OBJECT-TYPE
--		SYNTAX 			DisplayString
--		MAX-ACCESS		read-write
--		STATUS			current
--		DESCRIPTION 
--		"
--		The user name of the dedicated destination.							
--		"
--		::= {bmcDedicatedDestinationEntry 9} 
--	bmcDedicatedDestinationEmailSubject OBJECT-TYPE
--		SYNTAX 			DisplayString
--		MAX-ACCESS		read-write
--		STATUS			current
--		DESCRIPTION 
--		"
--		The email subject of the dedicated destination.							
--		"
--		::= {bmcDedicatedDestinationEntry 10} 
--	bmcDedicatedDestinationEmailMessage OBJECT-TYPE
--		SYNTAX 			DisplayString
--		MAX-ACCESS		read-write
--		STATUS			current
--		DESCRIPTION 
--		"
--		The email message of the dedicated destination.							
--		"
--		::= {bmcDedicatedDestinationEntry 11} 
--	bmcDedicatedDestinationAuthPro OBJECT-TYPE
--		SYNTAX 			Integer32{
--						none(0),
--						sha(1),
--						md5(2)
--						}
--		MAX-ACCESS		read-write
--		STATUS			current
--		DESCRIPTION 
--		"
--		The AuthPro of the dedicated destination.							
--		"
--		::= {bmcDedicatedDestinationEntry 12}
--	bmcDedicatedDestinationPrivPro OBJECT-TYPE
--		SYNTAX 			Integer32{
--						none(0),
--						des(1),
--						aes(2)
--						}
--		MAX-ACCESS		read-write
--		STATUS			current
--		DESCRIPTION 
--		"
--		The PrivPro of the dedicated destination.							
--		"
--		::= {bmcDedicatedDestinationEntry 13}
--	bmcDedicatedDestinationAuthPwd OBJECT-TYPE
--		SYNTAX 			DisplayString
--		MAX-ACCESS		read-write
--		STATUS			current
--		DESCRIPTION 
--		"
--		The AuthPwd of the dedicated destination.							
--		"
--		::= {bmcDedicatedDestinationEntry 14}
--	bmcDedicatedDestinationPrivPwd OBJECT-TYPE
--		SYNTAX 			DisplayString
--		MAX-ACCESS		read-write
--		STATUS			current
--		DESCRIPTION 
--		"
--		The PrivPwd of the dedicated destination.							
--		"
--		::= {bmcDedicatedDestinationEntry 15}
--	bmcDedicatedDestinationEngineId OBJECT-TYPE
--		SYNTAX 			DisplayString
--		MAX-ACCESS		read-write
--		STATUS			current
--		DESCRIPTION 
--		"
--		The EngineId of the dedicated destination.							
--		"
--		::= {bmcDedicatedDestinationEntry 16}
--		::= {bmcDedicatedDestinationEntry 12}
--bmcDedicatedDestinationTable end
--bmcSharedDestinationTable start
--	bmcSharedDestinationTable	OBJECT-TYPE
--	    SYNTAX     SEQUENCE OF bmcSharedDestinationEntry
--	    MAX-ACCESS not-accessible
--	    STATUS     current
--	    DESCRIPTION
--	    "
--	    The table of service information.
--	    "
--		::= {platformEventFilters 4}
--	bmcSharedDestinationEntry OBJECT-TYPE
--	    SYNTAX     bmcSharedDestinationEntry
--	    MAX-ACCESS not-accessible
--	    STATUS     current
--	    DESCRIPTION
--	           ""
--	    INDEX   { 
--				  bmcSharedDestinationIndex                
--	            }
--	    ::= { bmcSharedDestinationTable 1 }   
--	
--	bmcSharedDestinationEntry ::= SEQUENCE {
--		bmcSharedDestinationIndex			Integer32,
--		bmcSharedDestinationID				Integer32,
--		bmcSharedDestinationType			Integer32,
--		bmcSharedDestinationTypeVersion		Integer32,
--	    bmcSharedDestinationAddress			DisplayString,
--		bmcSharedDestinationTypePort		Integer32,
--		bmcSharedDestinationTrapUserName	DisplayString,
--		bmcSharedDestinationTrapCommunity   DisplayString,
--	    bmcSharedDestinationUserName		DisplayString,
--		bmcSharedDestinationEmailSubject	DisplayString,
--		bmcSharedDestinationEmailMessage	DisplayString,
--		bmcSharedDestinationAuthPro		Integer32,
--		bmcSharedDestinationPrivPro		Integer32,
--		bmcSharedDestinationAuthPwd	DisplayString,
--		bmcSharedDestinationPrivPwd	DisplayString,
--		bmcSharedDestinationEngineId	DisplayString
--	}
--	bmcSharedDestinationIndex OBJECT-TYPE
--		SYNTAX 			Integer32
--		MAX-ACCESS		read-only
--		STATUS			current
--		DESCRIPTION 
--		"
--		The index associated with the shared destination of this entry.	
--		"
--		::= {bmcSharedDestinationEntry 1}
--	bmcSharedDestinationID OBJECT-TYPE
--		SYNTAX 			Integer32
--		MAX-ACCESS		read-only
--		STATUS			current
--		DESCRIPTION 
--		"
--		The id of the shared destination.							
--		"
--		::= {bmcSharedDestinationEntry 2} 
--	bmcSharedDestinationType OBJECT-TYPE
--		SYNTAX 			Integer32{
--						snmp-trap(1),
--						e-mail(2)
--						}
--		MAX-ACCESS		read-write
--		STATUS			current
--		DESCRIPTION 
--		"
--		The type of the shared destination.							
--		"
--		::= {bmcSharedDestinationEntry 3} 
--	bmcSharedDestinationTypeVersion OBJECT-TYPE
--		SYNTAX 			Integer32{
--						none(0),
--						v1(1),
--						v2c(2),
--						v3(3)
--						}
--		MAX-ACCESS		read-write
--		STATUS			current
--		DESCRIPTION 
--		"
--		The mode of the shared destination.							
--		"
--		::= {bmcSharedDestinationEntry 4}
--	bmcSharedDestinationAddress OBJECT-TYPE
--		SYNTAX 			DisplayString
--		MAX-ACCESS		read-write
--		STATUS			current
--		DESCRIPTION 
--		"
--		The ip address of the shared destination.							
--		"
--		::= {bmcSharedDestinationEntry 5} 
--	bmcSharedDestinationTypePort OBJECT-TYPE
--		SYNTAX 			Integer32
--		MAX-ACCESS		read-write
--		STATUS			current
--		DESCRIPTION 
--		"
--		The port of the shared destination.							
--		"
--		::= {bmcSharedDestinationEntry 6}
--	bmcSharedDestinationTrapUserName OBJECT-TYPE
--		SYNTAX 			DisplayString
--		MAX-ACCESS		read-write
--		STATUS			current
--		DESCRIPTION 
--		"
--		The Trap UserName of the shared destination.							
--		"
--		::= {bmcSharedDestinationEntry 7}
--	bmcSharedDestinationTrapCommunity OBJECT-TYPE
--		SYNTAX 			DisplayString
--		MAX-ACCESS		read-write
--		STATUS			current
--		DESCRIPTION 
--		"
--		The Trap Community of the shared destination.							
--		"
--		::= {bmcSharedDestinationEntry 8}
--	bmcSharedDestinationUserName OBJECT-TYPE
--		SYNTAX 			DisplayString
--		MAX-ACCESS		read-write
--		STATUS			current
--		DESCRIPTION 
--		"
--		The user name of the shared destination.							
--		"
--		::= {bmcSharedDestinationEntry 9} 
--	bmcSharedDestinationEmailSubject OBJECT-TYPE
--		SYNTAX 			DisplayString
--		MAX-ACCESS		read-write
--		STATUS			current
--		DESCRIPTION 
--		"
--		The email subject of the shared destination.							
--		"
--		::= {bmcSharedDestinationEntry 10} 
--	bmcSharedDestinationEmailMessage OBJECT-TYPE
--		SYNTAX 			DisplayString
--		MAX-ACCESS		read-write
--		STATUS			current
--		DESCRIPTION 
--		"
--		The email message of the shared destination.							
--		"
--		::= {bmcSharedDestinationEntry 11}
--	bmcSharedDestinationAuthPro OBJECT-TYPE
--		SYNTAX 			Integer32{
--						none(0),
--						sha(1),
--						md5(2)
--						}
--		MAX-ACCESS		read-write
--		STATUS			current
--		DESCRIPTION 
--		"
--		The AuthPro of the shared destination.							
--		"
--		::= {bmcSharedDestinationEntry 12}
--	bmcSharedDestinationPrivPro OBJECT-TYPE
--		SYNTAX 			Integer32{
--						none(0),
--						des(1),
--						aes(2)
--						}
--		MAX-ACCESS		read-write
--		STATUS			current
--		DESCRIPTION 
--		"
--		The PrivPro of the shared destination.							
--		"
--		::= {bmcSharedDestinationEntry 13}
--	bmcSharedDestinationAuthPwd OBJECT-TYPE
--		SYNTAX 			DisplayString
--		MAX-ACCESS		read-write
--		STATUS			current
--		DESCRIPTION 
--		"
--		The AuthPwd of the shared destination.							
--		"
--		::= {bmcSharedDestinationEntry 14}
--	bmcSharedDestinationPrivPwd OBJECT-TYPE
--		SYNTAX 			DisplayString
--		MAX-ACCESS		read-write
--		STATUS			current
--		DESCRIPTION 
--		"
--		The PrivPwd of the shared destination.							
--		"
--		::= {bmcSharedDestinationEntry 15}
--	bmcSharedDestinationEngineId OBJECT-TYPE
--		SYNTAX 			DisplayString
--		MAX-ACCESS		read-write
--		STATUS			current
--		DESCRIPTION 
--		"
--		The EngineId of the shared destination.							
--		"
--		::= {bmcSharedDestinationEntry 16}
--		::= {bmcSharedDestinationEntry 12}
--bmcSharedDestinationTable end

--pamOrderTable start
--	pamOrderTable	OBJECT-TYPE
--	    SYNTAX     SEQUENCE OF pamOrderEntry
--	    MAX-ACCESS not-accessible
--	    STATUS     current
--	    DESCRIPTION
--	    "
--	    The table of pam order. If you want to change the PAM order, just set the corresponding service priority.
--	    "
--		::= {serverBmcInfo 19}
--	pamOrderEntry OBJECT-TYPE
--	    SYNTAX     pamOrderEntry
--	    MAX-ACCESS not-accessible
--	    STATUS     current
--	    DESCRIPTION
--	           ""
--	    INDEX   { 
--				  index                
--	            }
--	    ::= { pamOrderTable 1 }   
--	
--	pamOrderEntry ::= SEQUENCE {
--		index			Integer32,
--		pamOrderIPMI			Integer32,
--		pamOrderLDAP			Integer32,
--		pamOrderACTIVEDIRECTORY	Integer32,
--		pamOrderRADIUS			Integer32
--	}
--	index OBJECT-TYPE
--		SYNTAX 			Integer32
--		MAX-ACCESS		read-only
--		STATUS			current
--		DESCRIPTION 
--		"
--		The index associated with the pam order of this entry.	
--		"
--		::= {pamOrderEntry 1}
--	pamOrderIPMI OBJECT-TYPE
--		SYNTAX 			Integer32
--		MAX-ACCESS		read-write
--		STATUS			current
--		DESCRIPTION 
--		"
--		Enable critical events associated with the pam order of this entry. Set PAM order, you can choose 1-4.	
--		"
--		::= {pamOrderEntry 2}
--	pamOrderLDAP OBJECT-TYPE
--		SYNTAX 			Integer32
--		MAX-ACCESS		read-write
--		STATUS			current
--		DESCRIPTION 
--		"
--		Enable noncritical events associated with the pam order of this entry. Set PAM order, you can choose 1-4.	
--		"
--		::= {pamOrderEntry 3}
--	pamOrderACTIVEDIRECTORY OBJECT-TYPE
--		SYNTAX 			Integer32
--		MAX-ACCESS		read-write
--		STATUS			current
--		DESCRIPTION 
--		"
--		Enable nonrecoverable events associated with the pam order of this entry. Set PAM order ,you can choose 1-4.	
--		"
--		::= {pamOrderEntry 4}
--	pamOrderRADIUS OBJECT-TYPE
--		SYNTAX 			Integer32
--		MAX-ACCESS		read-only
--		STATUS			current
--		DESCRIPTION 
--		"
--		Enable fan state change events associated with the pam order of this entry. Set PAM order, you can choose 1-4.
--		"
--		::= {pamOrderEntry 5}
--pamOrderTable end
--logSettings start
	systemLogEnable  OBJECT-TYPE
		SYNTAX 			Integer32
						{
							disable(0),
							enable(1)
						}
		MAX-ACCESS		read-write
		STATUS			current
		DESCRIPTION 
		"
			The enable associated with the system log function.
		"
		::= {advancedLog 1}
	localLogEnable  OBJECT-TYPE
		SYNTAX 			Integer32
						{
							disable(0),
							enable(1)
						}
		MAX-ACCESS		read-write
		STATUS			current
		DESCRIPTION 
		"
			The enable associated with the local log function.
		"
		::= {advancedLog 2}
	remoteLogEnable  OBJECT-TYPE
		SYNTAX 			Integer32
						{
							disable(0),
							enable(1)
						}
		MAX-ACCESS		read-write
		STATUS			current
		DESCRIPTION 
		"
			The enable associated with the remote log function.
		"
		::= {advancedLog 3}
	securityLog  OBJECT-TYPE
		SYNTAX 			Integer32
						{
							disable(0),
							enable(1)
						}
		MAX-ACCESS		read-write
		STATUS			current
		DESCRIPTION 
		"
			The enable associated with the security log function.
		"
		::= {advancedLog 4}
	portType  OBJECT-TYPE
		SYNTAX 			Integer32
						{
							NONE(0),
							UDP(1),
							TCP(2)
						}
		MAX-ACCESS		read-write
		STATUS			current
		DESCRIPTION 
		"
			The port type associated with the remote server.
		"
		::= {advancedLog 5}
	logFileSize  OBJECT-TYPE
		SYNTAX 			Integer32
		MAX-ACCESS		read-write
		STATUS			current
		DESCRIPTION 
		"
			The file size associated with the log.
		"
		::= {advancedLog 6}
	rotateCount  OBJECT-TYPE
		SYNTAX 			Integer32
		MAX-ACCESS		read-write
		STATUS			current
		DESCRIPTION 
		"
			The totate count associated with the log.
		"
		::= {advancedLog 7}

	serverIdentitySource  OBJECT-TYPE
		SYNTAX 			Integer32
						{
							HostName(0),
							BoardSN(1),
							ProductAssetTag(2)
						}
		MAX-ACCESS		read-write
		STATUS			current
		DESCRIPTION 
		"
			The ServerIdentitySource type associated with the remote server.
		"
		::= {advancedLog 8}
	alarmSeverity  OBJECT-TYPE
		SYNTAX 			Integer32
						{
							Critical(3),
							Major(2),
							Minor(1),
							Normal(0)
						}
		MAX-ACCESS		read-write
		STATUS			current
		DESCRIPTION 
		"
			The port type associated with the remote server.
		"
		::= {advancedLog 9}
	operationLog  OBJECT-TYPE
		SYNTAX 			Integer32
						{
							disable(0),
							enable(1)
						}
		MAX-ACCESS		read-write
		STATUS			current
		DESCRIPTION 
		"
			The port type associated with the operation server.
		"
		::= {advancedLog 10}
	eventLog  OBJECT-TYPE
		SYNTAX 			Integer32
						{
							disable(0),
							enable(1)
						}
		MAX-ACCESS		read-write
		STATUS			current
		DESCRIPTION 
		"
			The port type associated with the remote server.
		"
		::= {advancedLog 11}
	remoteLogServer1  OBJECT-TYPE
		SYNTAX 			DisplayString
		MAX-ACCESS		read-write
		STATUS			current
		DESCRIPTION 
		"
			The server address associated with the remote server.
		"
		::= {advancedLog 12}
	remoteServerPort1  OBJECT-TYPE
		SYNTAX 			Integer32
		MAX-ACCESS		read-write
		STATUS			current
		DESCRIPTION 
		"
			The port associated with the remote server.
		"
		::= {advancedLog 13}
	remoteLogServer2  OBJECT-TYPE
		SYNTAX 			DisplayString
		MAX-ACCESS		read-write
		STATUS			current
		DESCRIPTION 
		"
			The server address associated with the remote server.
		"
		::= {advancedLog 14}
	remoteServerPort2  OBJECT-TYPE
		SYNTAX 			Integer32
		MAX-ACCESS		read-write
		STATUS			current
		DESCRIPTION 
		"
			The port associated with the remote server.
		"
		::= {advancedLog 15}
	remoteLogServer3  OBJECT-TYPE
		SYNTAX 			DisplayString
		MAX-ACCESS		read-write
		STATUS			current
		DESCRIPTION 
		"
			The server address associated with the remote server.
		"
		::= {advancedLog 16}
	remoteServerPort3  OBJECT-TYPE
		SYNTAX 			Integer32
		MAX-ACCESS		read-write
		STATUS			current
		DESCRIPTION 
		"
			The port associated with the remote server.
		"
		::= {advancedLog 17}
	remoteLogServer4  OBJECT-TYPE
		SYNTAX 			DisplayString
		MAX-ACCESS		read-write
		STATUS			current
		DESCRIPTION 
		"
			The server address associated with the remote server.
		"
		::= {advancedLog 18}
	remoteServerPort4  OBJECT-TYPE
		SYNTAX 			Integer32
		MAX-ACCESS		read-write
		STATUS			current
		DESCRIPTION 
		"
			The port associated with the remote server.
		"
		::= {advancedLog 19}
	logPolicyStatus  OBJECT-TYPE
		SYNTAX 			Integer32
						{
							linearStoragePolicy(0),
							circularStoragePolicy(1)
						}
		MAX-ACCESS		read-only
		STATUS			current
		DESCRIPTION 
		"
			The log policy.
		"
		::= {logPolicy 1}
	logPolicyControl  OBJECT-TYPE
		SYNTAX 			Integer32
						{
							linearStoragePolicy(0),
							circularStoragePolicy(1)
						}
		MAX-ACCESS		write-only
		STATUS			current
		DESCRIPTION 
		"
			Setting the log policy.
		"
		::= {logPolicy 2}
--logSettings end
--serviceSession start
	serviceSessionTable	OBJECT-TYPE
	    SYNTAX     SEQUENCE OF ServiceSessionEntry
	    MAX-ACCESS not-accessible
	    STATUS     current
	    DESCRIPTION
	    "
	    The table of dedicated interface information relevant to this entity's dedicated interface.
	    "
		::= {serviceSession 1}
	serviceSessionEntry OBJECT-TYPE
	    SYNTAX     ServiceSessionEntry
	    MAX-ACCESS not-accessible
	    STATUS     current
	    DESCRIPTION
	           "The dedicated interface information associated with the dedicated interface of this entry."
	    INDEX   { 
				  serviceSessionIndex		                
	            }
	    ::= { serviceSessionTable 1 }   
	
	ServiceSessionEntry ::= SEQUENCE {
		serviceSessionIndex		Integer32,
	    serviceSessionID		Integer32,
	    serviceSessionType		DisplayString,
		serviceSessionUserID	Integer32,
		serviceSessionUserName	DisplayString,
	    serviceSessionClientIP	DisplayString,
		serviceSessionPrivilege	DisplayString
	}
	serviceSessionIndex  OBJECT-TYPE
		SYNTAX 			Integer32
		MAX-ACCESS		read-only
		STATUS			current
		DESCRIPTION 
		"  
		The index of the session.
		"
		::= {serviceSessionEntry 1}           
	         
	serviceSessionID OBJECT-TYPE
		SYNTAX 			Integer32 
		MAX-ACCESS		read-only
		STATUS			current
		DESCRIPTION 
		"
		The session id of the session.
		"
		::= {serviceSessionEntry 2} 
	
	serviceSessionType OBJECT-TYPE
		SYNTAX 			DisplayString
		MAX-ACCESS		read-only
		STATUS			current
		DESCRIPTION 
		"
		The session type of the session.
		"
		::= {serviceSessionEntry 3}  
	
	serviceSessionUserID OBJECT-TYPE
		SYNTAX 			Integer32{
					NA(-1)
		}		
		MAX-ACCESS		read-only
		STATUS			current
		DESCRIPTION 
		"
		The user id of the session.
		"
		::= {serviceSessionEntry 4} 

	serviceSessionUserName OBJECT-TYPE
		SYNTAX 			DisplayString 
		MAX-ACCESS		read-only
		STATUS			current
		DESCRIPTION 
		"
		The user name of the session.
		"
		::= {serviceSessionEntry 5} 

	serviceSessionClientIP  OBJECT-TYPE
		SYNTAX 			DisplayString
		MAX-ACCESS		read-only
		STATUS			current
		DESCRIPTION 
		"
		The client ip of the session.
		"
		::= {serviceSessionEntry 6} 
	
	serviceSessionPrivilege OBJECT-TYPE
		SYNTAX 			DisplayString 
		MAX-ACCESS		read-only
		STATUS			current
		DESCRIPTION 
		"
		The privilege of the session.
		"
		::= {serviceSessionEntry 7}
	serviceSessionDelete OBJECT-TYPE
		SYNTAX 			Integer32 
		MAX-ACCESS		write-only
		STATUS			current
		DESCRIPTION 
		"
		Deleting session by session id.
		"
		::= {serviceSession 2}
--serviceSession end
--serverPowerControl start
	serverPowerStatus OBJECT-TYPE
		SYNTAX 			Integer32{
		    			powerOff(0),
			            powerOn(1)
		} 
		MAX-ACCESS		read-only
		STATUS			current
		DESCRIPTION 
		"
		Get the server current  status of the power for read.			
		0 for server power off;
		1 for server power on;					
		"
		::= {serverPowerControl 1}  
	serverPowerStatusControl OBJECT-TYPE
		SYNTAX 			Integer32{
		    			powerOff(0),
			            powerOn(1),
						powerCycle(2),
						hardReset(3),
						ACPIClose(4)
		} 
		MAX-ACCESS		write-only
		STATUS			current
		DESCRIPTION 
		"
		Set the server current status of the power .	
		0 for set server power off;
		1 for set server power on;
		2 for set server power cycle;
		3 for set server hard reset;
		4 for set server ACPI close;	
		read always return 0xff;				
		"
		::= {serverPowerControl 2}  
--serverPowerControl end
--serverLocatedControl start
	serverIDLEDStatus OBJECT-TYPE
		SYNTAX 			Integer32{
		    			ledOff(0),
			            ledOn(1),
						ledBlink(2)
		} 
		MAX-ACCESS		read-only
		STATUS			current
		DESCRIPTION 
		"
		Get the system ID LED  status.			
		0 for system ID LED  power off;
		1 for system ID LED  power on;	
				
		"
		::= {serverLocatedControl 1} 
	serverIDLEDStatusControl OBJECT-TYPE
		SYNTAX 			Integer32{
						ledOff(0),
						ledOn(1),
						ledBlink(2)
		}
		MAX-ACCESS		write-only
		STATUS			current
		DESCRIPTION 
		"
		Set the system ID LED  status.			
		0 for system ID LED  power off;
		other for system ID LED  power on time (seconds);	
		read always return 0xff;				
		"
		::= {serverLocatedControl 2}   
--serverLocatedControl end
--serverBootOptionControl start
	serverBootDev OBJECT-TYPE
		SYNTAX 			Integer32{
		    			bootdevNONE(0),
			            bootdevPXE(1),
						bootdevDISK(2),
						bootdevDIAG(3),
						bootdevCDROM(4),
						bootdevBIOS(5),
						bootdevFLOPPY(6),
						bootdevUSB(7)
		} 
		MAX-ACCESS		read-only
		STATUS			current
		DESCRIPTION 
		"
		Get the server current  boot option for read.			
		0 for do not change boot device order;
		1 for force PXE boot;
		2 for force boot from default Hard-drive;
		3 for force boot from Diagnostic Partition;
		4 for force boot from CD/DVD;
		5 for force boot into BIOS Setup;
		6 for force boot from Floppy removable media;
		7 for force boot from usb media;	
		"
		::= {serverBootOptionControl 1} 
	serverBootDevControl OBJECT-TYPE
		SYNTAX 			Integer32{
		    			bootdevNONE(0),
			            bootdevPXE(1),
						bootdevDISK(2),
						bootdevDIAG(3),
						bootdevCDROM(4),
						bootdevBIOS(5),
						bootdevFLOPPY(6),
						bootdevUSB(7)
		}
		MAX-ACCESS		write-only
		STATUS			current
		DESCRIPTION 
		"
		Set the server boot option of the chassis.			
		0 for do not change boot device order;
		1 for force PXE boot;
		2 for force boot from default Hard-drive;
		3 for force boot from Diagnostic Partition;
		4 for force boot from CD/DVD;
		5 for force boot into BIOS Setup;
		6 for force boot from Floppy removable media;
		7 for force boot from usb media;			
		"
		::= {serverBootOptionControl 2}   
--serverBootOptionControl end
--serverTemperatureInfo start
	inputtemperature1 OBJECT-TYPE
		SYNTAX OCTET STRING
		MAX-ACCESS read-only
		STATUS current
		DESCRIPTION
			""
		::= { serverTemperatureInfo 1 }
	inputtemperature2 OBJECT-TYPE
		SYNTAX OCTET STRING
		MAX-ACCESS read-only
		STATUS current
		DESCRIPTION
			""
		::= { serverTemperatureInfo 2 }          
--serverTemperatureInfo end 
--healthStatus start
	systemHealthStatus OBJECT-TYPE
		SYNTAX 			Integer32 { normal(0), abnormal(1), absent(2) }
		MAX-ACCESS		read-only
		STATUS			current
		DESCRIPTION 
		""
		::= {healthStatus 1}
	powerHealthStatus OBJECT-TYPE
		SYNTAX 			Integer32 { normal(0), abnormal(1), absent(2) }
		MAX-ACCESS		read-only
		STATUS			current
		DESCRIPTION 
		""
		::= {healthStatus 2}
	fanHealthStatus OBJECT-TYPE
		SYNTAX 			Integer32  { normal(0), abnormal(1), absent(2) }
		MAX-ACCESS		read-only
		STATUS			current
		DESCRIPTION 
		""
		::= {healthStatus 3} 
	cpuHealthStatus OBJECT-TYPE
		SYNTAX 			Integer32 { normal(0), abnormal(1), absent(2) }
		MAX-ACCESS		read-only
		STATUS			current
		DESCRIPTION 
		""
		::= {healthStatus 4} 
	memoryHealthStatus OBJECT-TYPE
		SYNTAX 			Integer32 { normal(0), abnormal(1), absent(2) }
		MAX-ACCESS		read-only
		STATUS			current
		DESCRIPTION 
		""
		::= {healthStatus 5} 
	diskHealthStatus OBJECT-TYPE
		SYNTAX 			Integer32 { normal(0), abnormal(1), absent(2) }
		MAX-ACCESS		read-only
		STATUS			current
		DESCRIPTION 
		""
		::= {healthStatus 6}
	pcieHealthStatus OBJECT-TYPE
		SYNTAX 			Integer32 { normal(0), abnormal(1), absent(2) }
		MAX-ACCESS		read-only
		STATUS			current
		DESCRIPTION 
		""
		::= {healthStatus 7} 
--healthStatus end
--hddStatus start
	hddStatusTable	OBJECT-TYPE
	    SYNTAX     SEQUENCE OF HddStatusEntry
	    MAX-ACCESS read-only
	    STATUS     current
	    DESCRIPTION
	    "
	    	The table of hddStatus information relevant to this entity's harddisk.
	    "
		::= {hddStatus 1}
	hddStatusEntry OBJECT-TYPE
	    SYNTAX     HddStatusEntry
	    MAX-ACCESS read-only
	    STATUS     current
	    DESCRIPTION
	    	"The Entry of hddStatus information relevant to this entity's harddisk."
	    INDEX   { 
				  hddStatusIndex		                
	            }
	    ::= { hddStatusTable 1 }   
	
	HddStatusEntry ::= SEQUENCE {
		hddStatusIndex		Integer32,
		hddLocation			DisplayString,
		hddHealth			Integer32,
		hddStatusDescription			DisplayString
	}
	hddStatusIndex  OBJECT-TYPE
		SYNTAX 			Integer32
		MAX-ACCESS		read-only
		STATUS			current
		DESCRIPTION 
		"  
			The index of the hdd.
		"
		::= {hddStatusEntry 1}           
	         

	hddLocation OBJECT-TYPE
		SYNTAX 			DisplayString
		MAX-ACCESS		read-only
		STATUS			current
		DESCRIPTION 
		"
			The name type of the hdd.
		"
		::= {hddStatusEntry 2}  
	hddHealth OBJECT-TYPE
		SYNTAX 			Integer32{ normal(0), abnormal(1), absent(2) }
		MAX-ACCESS		read-only
		STATUS			current
		DESCRIPTION 
		"
			The disk health associated with the hddName.
		"
		::= {hddStatusEntry 3}
	hddStatusDescription  OBJECT-TYPE
		SYNTAX 			DisplayString
		MAX-ACCESS		read-only
		STATUS			current
		DESCRIPTION 
		"
			The disk status associated with the hddName.
		"
		::= {hddStatusEntry 4}
--hddStatus end
END
